;; ====================================================================
;; コマンド名 : KP
;; 機能概要   : 指定した2点（基準線）から50離れた位置に、
;;              上辺を両端50ずつ短縮した台形ポリラインを自動作成する
;; 仕様       : 基準離れ 50 / 高さ 50 / 上辺両端短縮 50 / Undo1回対応
;; ====================================================================

(defun c:KP ( / p1 p2 pickPt ang sideAng dist h shorten p1_base p2_base p1_top p2_top )
  (vl-load-com)
  
  ;; Undo（元に戻す）のグループ化開始
  (vla-StartUndoMark (vla-get-ActiveDocument (vlax-get-acad-object)))
  
  ;; ------------------------------------------------------------------
  ;; 寸法・パラメータ設定
  ;; ------------------------------------------------------------------
  (setq dist 50.0)    ; 基準線から脚端までのオフセット距離
  (setq h 50.0)       ; 形状の高さ（短辺）
  (setq shorten 50.0) ; 上辺（長辺）の左右短縮量
  
  ;; ------------------------------------------------------------------
  ;; 1. 基準線（2点）の入力指定
  ;; ------------------------------------------------------------------
  (setq p1 (getpoint "\n基準線の1点目を指定: "))
  (if p1
    (setq p2 (getpoint p1 "\n基準線の2点目を指定: "))
  )
  
  (if (and p1 p2)
    (progn
      ;; 基準線の角度取得
      (setq ang (angle p1 p2))
      
      ;; --------------------------------------------------------------
      ;; 2. 作図方向の判定
      ;; --------------------------------------------------------------
      (setq pickPt (getpoint p2 "\n作図する方向をクリック: "))
      
      (if pickPt
        (progn
          ;; 外積判定によりクリックした方向の垂直角度（±90度）を算出
          (if (< (sin (- (angle p1 pickPt) ang)) 0)
            (setq sideAng (- ang (/ pi 2.0)))
            (setq sideAng (+ ang (/ pi 2.0)))
          )
          
          ;; ----------------------------------------------------------
          ;; 3. 各頂点の座標計算
          ;; ----------------------------------------------------------
          ;; ① 脚の先端（基準線から50離した位置）
          (setq p1_base (polar p1 sideAng dist))
          (setq p2_base (polar p2 sideAng dist))
          
          ;; ② 天井の長辺（基準線から100離し、かつ両端を内側へ50短縮）
          (setq p1_top (polar (polar p1 sideAng (+ dist h)) ang shorten))
          (setq p2_top (polar (polar p2 sideAng (+ dist h)) (+ ang pi) shorten))
          
          ;; ----------------------------------------------------------
          ;; 4. ポリラインの生成
          ;; ----------------------------------------------------------
          (command "_.pline" "_non" p1_base "_non" p1_top "_non" p2_top "_non" p2_base "")
          
          (princ "\n台形ポリライン（上辺50短縮・50オフセット）を作成しました。")
        )
      )
    )
    (princ "\n点の指定がキャンセルされました。")
  )
  
  ;; Undoグループ化終了
  (vla-EndUndoMark (vla-get-ActiveDocument (vlax-get-acad-object)))
  (princ)
)

(princ "\n コマンドがロードされました。")
(princ)
