;;; ============================================================
;;;  IJCAD用 AutoLISP (QSBコマンド) - PowerShell/WPF UI版
;;;  ブロックエディタ(BEDIT)を開かずに、選択したブロックの内部にある
;;;  すべての線・図形の画層・線種・線種尺度・色・線の太さを一括変更する
;;;  ブロック内のハッチング・2Dソリッドの分解・削除にも対応
;;;   - パターンハッチング / 塗りつぶしハッチング(SOLID・グラデーション) / 2Dソリッド
;;;     を、それぞれ「そのまま / 分解 / 削除」から選ぶ
;;;   - 分解 : 塗りつぶし・模様を消して、境界を輪郭線(ポリライン)で作り直す
;;;            (楕円・スプラインの境界は、その図形のまま作る)
;;;   - 画層などの変更の適用先を「すべて / ハッチング・ソリッドのみ / それ以外のみ」から選べる
;;;   - 線種尺度 : 「すべての図形に一括」か「選んだ線種の図形だけ」かを選べる
;;;                (線種は複数選択可。線種の判定は、線種を変更する前の線種で行う)
;;;   - 色の詳細パレット(10-249)と番号入力は、「詳細な色番号」を押したときだけ表示
;;;  入れ子のブロックの中身も対象。変更はまとめて1回の元に戻す(U)で戻せる
;;;  UI : 画層の絞り込み検索、図面内の全画層・全線種から選択、AutoCAD配色の色パレット、
;;;       線の太さは標準値から選択、変更内容のプレビュー、Enter=適用 / Esc=キャンセル
;;;  ※通常ブロックを対象に想定。ダイナミックブロックは未検証。
;;; ============================================================

(vl-load-com)

;; --- WScript.ShellでPowerShellを同期起動 -----------------------------
(defun qsbc-run-ps1 (ps1Path inPath outPath / wsh cmd)
  (setq wsh (vlax-create-object "WScript.Shell"))
  (setq cmd (strcat
              "powershell.exe -NoProfile -ExecutionPolicy Bypass -WindowStyle Hidden -File "
              "\"" ps1Path "\" -InputPath \"" inPath "\" -OutputPath \"" outPath "\""
            ))
  (vlax-invoke-method wsh 'Run cmd 0 :vlax-true)
  (vlax-release-object wsh)
  (princ)
)

;; --- 埋め込みPowerShell(WPF)スクリプトの書き出し ----------------------
(defun qsbc-write-ps1-script (path / fn)
  (setq fn (open path "w"))
  (write-line "[CmdletBinding()]" fn)
  (write-line "param(" fn)
  (write-line "    [Parameter(Mandatory=$true)][string]$InputPath," fn)
  (write-line "    [Parameter(Mandatory=$true)][string]$OutputPath" fn)
  (write-line ")" fn)
  (write-line "Add-Type -AssemblyName PresentationFramework" fn)
  (write-line "Add-Type -AssemblyName PresentationCore" fn)
  (write-line "Add-Type -AssemblyName WindowsBase" fn)
  (write-line "" fn)
  (write-line "$NONE = '__NONE__'" fn)
  (write-line "$TAB = [string][char]9" fn)
  (write-line "" fn)
  (write-line "function Read-InputData ($path) {" fn)
  (write-line "    $d = @{ Names = @(); Layers = @(); AllLayers = @(); Ltypes = @(); AllLtypes = @(); Colors = @(); Lwts = @(); Ltscales = @(); EntCount = '0'; BlkCount = '0'; Hatch = '0'; Fill = '0'; Solid = '0' }" fn)
  (write-line "    $cur = $null" fn)
  (write-line "    if (Test-Path -LiteralPath $path) {" fn)
  (write-line "        foreach ($line in (Get-Content -LiteralPath $path -Encoding Default)) {" fn)
  (write-line "            if ($line -match '^###(.+)###$') { $cur = $Matches[1]; continue }" fn)
  (write-line "            if ($line -eq '') { continue }" fn)
  (write-line "            switch ($cur) {" fn)
  (write-line "                'NAMES'     { $d.Names += $line }" fn)
  (write-line "                'LAYERS'    { $d.Layers += $line }" fn)
  (write-line "                'ALLLAYERS' { $d.AllLayers += $line }" fn)
  (write-line "                'LTYPES'    { $d.Ltypes += $line }" fn)
  (write-line "                'ALLLTYPES' { $d.AllLtypes += $line }" fn)
  (write-line "                'COLORS'    { $d.Colors += $line }" fn)
  (write-line "                'LWTS'      { $d.Lwts += $line }" fn)
  (write-line "                'LTSCALES'  { $d.Ltscales += $line }" fn)
  (write-line "                'ENTCOUNT'  { $d.EntCount = $line }" fn)
  (write-line "                'BLKCOUNT'  { $d.BlkCount = $line }" fn)
  (write-line "                'HATCH'     { $d.Hatch = $line }" fn)
  (write-line "                'FILL'      { $d.Fill = $line }" fn)
  (write-line "                'SOLID'     { $d.Solid = $line }" fn)
  (write-line "            }" fn)
  (write-line "        }" fn)
  (write-line "    }" fn)
  (write-line "    return $d" fn)
  (write-line "}" fn)
  (write-line "" fn)
  (write-line "# ---------- ACI(色番号) → RGB ----------" fn)
  (write-line "function Get-AciRgb ([int]$i) {" fn)
  (write-line "    switch ($i) {" fn)
  (write-line "        1 { return @(255,0,0) }" fn)
  (write-line "        2 { return @(255,255,0) }" fn)
  (write-line "        3 { return @(0,255,0) }" fn)
  (write-line "        4 { return @(0,255,255) }" fn)
  (write-line "        5 { return @(0,0,255) }" fn)
  (write-line "        6 { return @(255,0,255) }" fn)
  (write-line "        7 { return @(255,255,255) }" fn)
  (write-line "        8 { return @(128,128,128) }" fn)
  (write-line "        9 { return @(192,192,192) }" fn)
  (write-line "    }" fn)
  (write-line "    if ($i -le 0 -or $i -gt 255) { return @(255,255,255) }" fn)
  (write-line "    if ($i -ge 250) { $g = [int][math]::Round(51 + ($i - 250) * 40.8); return @($g,$g,$g) }" fn)
  (write-line "    $hue = [math]::Floor(($i - 10) / 10) * 15.0" fn)
  (write-line "    $shade = ($i - 10) % 10" fn)
  (write-line "    $vals = @(1.0, 0.8, 0.6, 0.5, 0.3)" fn)
  (write-line "    $v = $vals[[int][math]::Floor($shade / 2)]" fn)
  (write-line "    $s = 1.0" fn)
  (write-line "    if ($shade % 2 -eq 1) { $s = 0.5 }" fn)
  (write-line "    $c = $v * $s" fn)
  (write-line "    $h = $hue / 60.0" fn)
  (write-line "    $x = $c * (1 - [math]::Abs(($h % 2) - 1))" fn)
  (write-line "    $m = $v - $c" fn)
  (write-line "    switch ([int][math]::Floor($h)) {" fn)
  (write-line "        0 { $r = $c; $g = $x; $b = 0 }" fn)
  (write-line "        1 { $r = $x; $g = $c; $b = 0 }" fn)
  (write-line "        2 { $r = 0; $g = $c; $b = $x }" fn)
  (write-line "        3 { $r = 0; $g = $x; $b = $c }" fn)
  (write-line "        4 { $r = $x; $g = 0; $b = $c }" fn)
  (write-line "        default { $r = $c; $g = 0; $b = $x }" fn)
  (write-line "    }" fn)
  (write-line "    return @([int][math]::Round(($r + $m) * 255), [int][math]::Round(($g + $m) * 255), [int][math]::Round(($b + $m) * 255))" fn)
  (write-line "}" fn)
  (write-line "" fn)
  (write-line "function New-RgbBrush ($rgb) {" fn)
  (write-line "    return New-Object System.Windows.Media.SolidColorBrush ([System.Windows.Media.Color]::FromRgb([byte]$rgb[0], [byte]$rgb[1], [byte]$rgb[2]))" fn)
  (write-line "}" fn)
  (write-line "" fn)
  (write-line "$inputData = Read-InputData -path $InputPath" fn)
  (write-line "" fn)
  (write-line "$xaml = @'" fn)
  (write-line "<Window xmlns=\"http://schemas.microsoft.com/winfx/2006/xaml/presentation\"" fn)
  (write-line "        xmlns:x=\"http://schemas.microsoft.com/winfx/2006/xaml\"" fn)
  (write-line "        Title=\"ブロック内部一括編集\" Width=\"1240\" Height=\"810\" MinWidth=\"1100\" MinHeight=\"700\"" fn)
  (write-line "        WindowStartupLocation=\"CenterScreen\" ResizeMode=\"CanResize\"" fn)
  (write-line "        Background=\"#F5F6F8\" Foreground=\"#1F2328\" FontFamily=\"Meiryo UI\" FontSize=\"13\"" fn)
  (write-line "        UseLayoutRounding=\"True\" TextOptions.TextFormattingMode=\"Display\">" fn)
  (write-line "  <Window.Resources>" fn)
  (write-line "    <Style x:Key=\"Card\" TargetType=\"Border\">" fn)
  (write-line "      <Setter Property=\"Background\" Value=\"#FFFFFF\"/>" fn)
  (write-line "      <Setter Property=\"BorderBrush\" Value=\"#E4E7EC\"/>" fn)
  (write-line "      <Setter Property=\"BorderThickness\" Value=\"1\"/>" fn)
  (write-line "      <Setter Property=\"CornerRadius\" Value=\"8\"/>" fn)
  (write-line "      <Setter Property=\"Padding\" Value=\"14,12\"/>" fn)
  (write-line "    </Style>" fn)
  (write-line "    <Style x:Key=\"CardTitle\" TargetType=\"TextBlock\">" fn)
  (write-line "      <Setter Property=\"FontSize\" Value=\"14\"/>" fn)
  (write-line "      <Setter Property=\"FontWeight\" Value=\"SemiBold\"/>" fn)
  (write-line "      <Setter Property=\"Foreground\" Value=\"#101828\"/>" fn)
  (write-line "    </Style>" fn)
  (write-line "    <Style x:Key=\"CardSub\" TargetType=\"TextBlock\">" fn)
  (write-line "      <Setter Property=\"FontSize\" Value=\"12\"/>" fn)
  (write-line "      <Setter Property=\"Foreground\" Value=\"#667085\"/>" fn)
  (write-line "      <Setter Property=\"Margin\" Value=\"0,3,0,0\"/>" fn)
  (write-line "      <Setter Property=\"TextTrimming\" Value=\"CharacterEllipsis\"/>" fn)
  (write-line "    </Style>" fn)
  (write-line "    <Style x:Key=\"Chip\" TargetType=\"Button\">" fn)
  (write-line "      <Setter Property=\"Background\" Value=\"#FFFFFF\"/>" fn)
  (write-line "      <Setter Property=\"Foreground\" Value=\"#344054\"/>" fn)
  (write-line "      <Setter Property=\"BorderBrush\" Value=\"#D0D5DD\"/>" fn)
  (write-line "      <Setter Property=\"Padding\" Value=\"11,4\"/>" fn)
  (write-line "      <Setter Property=\"Margin\" Value=\"0,0,6,6\"/>" fn)
  (write-line "      <Setter Property=\"FontSize\" Value=\"12\"/>" fn)
  (write-line "      <Setter Property=\"Cursor\" Value=\"Hand\"/>" fn)
  (write-line "      <Setter Property=\"Focusable\" Value=\"False\"/>" fn)
  (write-line "      <Setter Property=\"Template\">" fn)
  (write-line "        <Setter.Value>" fn)
  (write-line "          <ControlTemplate TargetType=\"Button\">" fn)
  (write-line "            <Border x:Name=\"bd\" Background=\"{TemplateBinding Background}\" BorderBrush=\"{TemplateBinding BorderBrush}\"" fn)
  (write-line "                    BorderThickness=\"1\" CornerRadius=\"13\" Padding=\"{TemplateBinding Padding}\" RenderTransformOrigin=\"0.5,0.5\">" fn)
  (write-line "              <Border.RenderTransform><ScaleTransform x:Name=\"ps\" ScaleX=\"1\" ScaleY=\"1\"/></Border.RenderTransform>" fn)
  (write-line "              <ContentPresenter HorizontalAlignment=\"Center\" VerticalAlignment=\"Center\"/>" fn)
  (write-line "            </Border>" fn)
  (write-line "            <ControlTemplate.Triggers>" fn)
  (write-line "              <Trigger Property=\"IsMouseOver\" Value=\"True\">" fn)
  (write-line "                <Setter TargetName=\"bd\" Property=\"Background\" Value=\"#F2F4F7\"/>" fn)
  (write-line "              </Trigger>" fn)
  (write-line "              <Trigger Property=\"Tag\" Value=\"sel\">" fn)
  (write-line "                <Setter TargetName=\"bd\" Property=\"Background\" Value=\"#EFF4FF\"/>" fn)
  (write-line "                <Setter TargetName=\"bd\" Property=\"BorderBrush\" Value=\"#2563EB\"/>" fn)
  (write-line "                <Setter Property=\"Foreground\" Value=\"#1D4ED8\"/>" fn)
  (write-line "              </Trigger>" fn)
  (write-line "              <Trigger Property=\"Tag\" Value=\"danger\">" fn)
  (write-line "                <Setter TargetName=\"bd\" Property=\"Background\" Value=\"#FEF3F2\"/>" fn)
  (write-line "                <Setter TargetName=\"bd\" Property=\"BorderBrush\" Value=\"#F04438\"/>" fn)
  (write-line "                <Setter Property=\"Foreground\" Value=\"#B42318\"/>" fn)
  (write-line "              </Trigger>" fn)
  (write-line "              <Trigger Property=\"IsPressed\" Value=\"True\">" fn)
  (write-line "                <Trigger.EnterActions><BeginStoryboard><Storyboard>" fn)
  (write-line "                  <DoubleAnimation Storyboard.TargetName=\"ps\" Storyboard.TargetProperty=\"ScaleX\" To=\"0.94\" Duration=\"0:0:0.07\"/>" fn)
  (write-line "                  <DoubleAnimation Storyboard.TargetName=\"ps\" Storyboard.TargetProperty=\"ScaleY\" To=\"0.94\" Duration=\"0:0:0.07\"/>" fn)
  (write-line "                </Storyboard></BeginStoryboard></Trigger.EnterActions>" fn)
  (write-line "                <Trigger.ExitActions><BeginStoryboard><Storyboard>" fn)
  (write-line "                  <DoubleAnimation Storyboard.TargetName=\"ps\" Storyboard.TargetProperty=\"ScaleX\" To=\"1\" Duration=\"0:0:0.15\" DecelerationRatio=\"0.8\"/>" fn)
  (write-line "                  <DoubleAnimation Storyboard.TargetName=\"ps\" Storyboard.TargetProperty=\"ScaleY\" To=\"1\" Duration=\"0:0:0.15\" DecelerationRatio=\"0.8\"/>" fn)
  (write-line "                </Storyboard></BeginStoryboard></Trigger.ExitActions>" fn)
  (write-line "              </Trigger>" fn)
  (write-line "            </ControlTemplate.Triggers>" fn)
  (write-line "          </ControlTemplate>" fn)
  (write-line "        </Setter.Value>" fn)
  (write-line "      </Setter>" fn)
  (write-line "    </Style>" fn)
  (write-line "    <Style x:Key=\"Swatch\" TargetType=\"Button\">" fn)
  (write-line "      <Setter Property=\"Width\" Value=\"15\"/>" fn)
  (write-line "      <Setter Property=\"Height\" Value=\"15\"/>" fn)
  (write-line "      <Setter Property=\"Margin\" Value=\"1\"/>" fn)
  (write-line "      <Setter Property=\"Cursor\" Value=\"Hand\"/>" fn)
  (write-line "      <Setter Property=\"Focusable\" Value=\"False\"/>" fn)
  (write-line "      <Setter Property=\"Template\">" fn)
  (write-line "        <Setter.Value>" fn)
  (write-line "          <ControlTemplate TargetType=\"Button\">" fn)
  (write-line "            <Grid>" fn)
  (write-line "              <Border x:Name=\"fill\" Background=\"{TemplateBinding Background}\" CornerRadius=\"3\" BorderBrush=\"#26000000\" BorderThickness=\"1\"/>" fn)
  (write-line "              <Border x:Name=\"ring\" CornerRadius=\"5\" Margin=\"-3\" BorderBrush=\"#101828\" BorderThickness=\"2\" Visibility=\"Collapsed\" IsHitTestVisible=\"False\"/>" fn)
  (write-line "            </Grid>" fn)
  (write-line "            <ControlTemplate.Triggers>" fn)
  (write-line "              <Trigger Property=\"IsMouseOver\" Value=\"True\">" fn)
  (write-line "                <Setter TargetName=\"fill\" Property=\"BorderBrush\" Value=\"#101828\"/>" fn)
  (write-line "                <Setter Property=\"Panel.ZIndex\" Value=\"5\"/>" fn)
  (write-line "              </Trigger>" fn)
  (write-line "              <Trigger Property=\"Tag\" Value=\"sel\">" fn)
  (write-line "                <Setter TargetName=\"ring\" Property=\"Visibility\" Value=\"Visible\"/>" fn)
  (write-line "                <Setter Property=\"Panel.ZIndex\" Value=\"10\"/>" fn)
  (write-line "              </Trigger>" fn)
  (write-line "            </ControlTemplate.Triggers>" fn)
  (write-line "          </ControlTemplate>" fn)
  (write-line "        </Setter.Value>" fn)
  (write-line "      </Setter>" fn)
  (write-line "    </Style>" fn)
  (write-line "    <Style x:Key=\"Btn\" TargetType=\"Button\">" fn)
  (write-line "      <Setter Property=\"Background\" Value=\"#FFFFFF\"/>" fn)
  (write-line "      <Setter Property=\"Foreground\" Value=\"#344054\"/>" fn)
  (write-line "      <Setter Property=\"BorderBrush\" Value=\"#D0D5DD\"/>" fn)
  (write-line "      <Setter Property=\"Padding\" Value=\"18,7\"/>" fn)
  (write-line "      <Setter Property=\"MinWidth\" Value=\"104\"/>" fn)
  (write-line "      <Setter Property=\"Cursor\" Value=\"Hand\"/>" fn)
  (write-line "      <Setter Property=\"Focusable\" Value=\"False\"/>" fn)
  (write-line "      <Setter Property=\"Template\">" fn)
  (write-line "        <Setter.Value>" fn)
  (write-line "          <ControlTemplate TargetType=\"Button\">" fn)
  (write-line "            <Border x:Name=\"bd\" Background=\"{TemplateBinding Background}\" BorderBrush=\"{TemplateBinding BorderBrush}\"" fn)
  (write-line "                    BorderThickness=\"1\" CornerRadius=\"6\" Padding=\"{TemplateBinding Padding}\">" fn)
  (write-line "              <ContentPresenter HorizontalAlignment=\"Center\" VerticalAlignment=\"Center\"/>" fn)
  (write-line "            </Border>" fn)
  (write-line "            <ControlTemplate.Triggers>" fn)
  (write-line "              <Trigger Property=\"IsMouseOver\" Value=\"True\"><Setter TargetName=\"bd\" Property=\"Opacity\" Value=\"0.85\"/></Trigger>" fn)
  (write-line "              <Trigger Property=\"IsPressed\" Value=\"True\"><Setter TargetName=\"bd\" Property=\"Opacity\" Value=\"0.7\"/></Trigger>" fn)
  (write-line "              <Trigger Property=\"IsEnabled\" Value=\"False\"><Setter TargetName=\"bd\" Property=\"Opacity\" Value=\"0.4\"/></Trigger>" fn)
  (write-line "            </ControlTemplate.Triggers>" fn)
  (write-line "          </ControlTemplate>" fn)
  (write-line "        </Setter.Value>" fn)
  (write-line "      </Setter>" fn)
  (write-line "    </Style>" fn)
  (write-line "    <Style x:Key=\"Primary\" TargetType=\"Button\" BasedOn=\"{StaticResource Btn}\">" fn)
  (write-line "      <Setter Property=\"Background\" Value=\"#2563EB\"/>" fn)
  (write-line "      <Setter Property=\"Foreground\" Value=\"#FFFFFF\"/>" fn)
  (write-line "      <Setter Property=\"BorderBrush\" Value=\"#2563EB\"/>" fn)
  (write-line "      <Setter Property=\"FontWeight\" Value=\"SemiBold\"/>" fn)
  (write-line "    </Style>" fn)
  (write-line "    <Style TargetType=\"ListBox\">" fn)
  (write-line "      <Setter Property=\"BorderThickness\" Value=\"0\"/>" fn)
  (write-line "      <Setter Property=\"Background\" Value=\"Transparent\"/>" fn)
  (write-line "      <Setter Property=\"ScrollViewer.HorizontalScrollBarVisibility\" Value=\"Disabled\"/>" fn)
  (write-line "    </Style>" fn)
  (write-line "    <Style TargetType=\"ListBoxItem\">" fn)
  (write-line "      <Setter Property=\"Padding\" Value=\"10,6\"/>" fn)
  (write-line "      <Setter Property=\"Cursor\" Value=\"Hand\"/>" fn)
  (write-line "      <Setter Property=\"FocusVisualStyle\" Value=\"{x:Null}\"/>" fn)
  (write-line "      <Setter Property=\"HorizontalContentAlignment\" Value=\"Stretch\"/>" fn)
  (write-line "      <Setter Property=\"Template\">" fn)
  (write-line "        <Setter.Value>" fn)
  (write-line "          <ControlTemplate TargetType=\"ListBoxItem\">" fn)
  (write-line "            <Grid Margin=\"0,1\">" fn)
  (write-line "              <Border x:Name=\"bd\" Background=\"Transparent\" CornerRadius=\"6\" Padding=\"{TemplateBinding Padding}\">" fn)
  (write-line "                <ContentPresenter HorizontalAlignment=\"{TemplateBinding HorizontalContentAlignment}\"/>" fn)
  (write-line "              </Border>" fn)
  (write-line "              <Border x:Name=\"bar\" Width=\"3\" HorizontalAlignment=\"Left\" Margin=\"0,6\" CornerRadius=\"2\" Background=\"#2563EB\" Visibility=\"Collapsed\"/>" fn)
  (write-line "            </Grid>" fn)
  (write-line "            <ControlTemplate.Triggers>" fn)
  (write-line "              <Trigger Property=\"IsMouseOver\" Value=\"True\"><Setter TargetName=\"bd\" Property=\"Background\" Value=\"#F2F4F7\"/></Trigger>" fn)
  (write-line "              <Trigger Property=\"IsSelected\" Value=\"True\">" fn)
  (write-line "                <Setter TargetName=\"bd\" Property=\"Background\" Value=\"#EFF4FF\"/>" fn)
  (write-line "                <Setter TargetName=\"bar\" Property=\"Visibility\" Value=\"Visible\"/>" fn)
  (write-line "              </Trigger>" fn)
  (write-line "            </ControlTemplate.Triggers>" fn)
  (write-line "          </ControlTemplate>" fn)
  (write-line "        </Setter.Value>" fn)
  (write-line "      </Setter>" fn)
  (write-line "    </Style>" fn)
  (write-line "    <Style x:Key=\"MatComboItem\" TargetType=\"ComboBoxItem\">" fn)
  (write-line "      <Setter Property=\"Padding\" Value=\"12,9\"/>" fn)
  (write-line "      <Setter Property=\"Cursor\" Value=\"Hand\"/>" fn)
  (write-line "      <Setter Property=\"FocusVisualStyle\" Value=\"{x:Null}\"/>" fn)
  (write-line "      <Setter Property=\"Template\">" fn)
  (write-line "        <Setter.Value>" fn)
  (write-line "          <ControlTemplate TargetType=\"ComboBoxItem\">" fn)
  (write-line "            <Border x:Name=\"bd\" Background=\"Transparent\" CornerRadius=\"6\" Padding=\"{TemplateBinding Padding}\">" fn)
  (write-line "              <ContentPresenter/>" fn)
  (write-line "            </Border>" fn)
  (write-line "            <ControlTemplate.Triggers>" fn)
  (write-line "              <Trigger Property=\"IsHighlighted\" Value=\"True\"><Setter TargetName=\"bd\" Property=\"Background\" Value=\"#F2F4F7\"/></Trigger>" fn)
  (write-line "              <Trigger Property=\"IsSelected\" Value=\"True\">" fn)
  (write-line "                <Setter TargetName=\"bd\" Property=\"Background\" Value=\"#EFF4FF\"/>" fn)
  (write-line "                <Setter Property=\"Foreground\" Value=\"#1D4ED8\"/>" fn)
  (write-line "              </Trigger>" fn)
  (write-line "            </ControlTemplate.Triggers>" fn)
  (write-line "          </ControlTemplate>" fn)
  (write-line "        </Setter.Value>" fn)
  (write-line "      </Setter>" fn)
  (write-line "    </Style>" fn)
  (write-line "    <Style x:Key=\"MatCombo\" TargetType=\"ComboBox\">" fn)
  (write-line "      <Setter Property=\"Foreground\" Value=\"#101828\"/>" fn)
  (write-line "      <Setter Property=\"Cursor\" Value=\"Hand\"/>" fn)
  (write-line "      <Setter Property=\"ItemContainerStyle\" Value=\"{StaticResource MatComboItem}\"/>" fn)
  (write-line "      <Setter Property=\"Template\">" fn)
  (write-line "        <Setter.Value>" fn)
  (write-line "          <ControlTemplate TargetType=\"ComboBox\">" fn)
  (write-line "            <Grid>" fn)
  (write-line "              <ToggleButton x:Name=\"tb\" Focusable=\"False\" ClickMode=\"Press\" IsChecked=\"{Binding Path=IsDropDownOpen, Mode=TwoWay, RelativeSource={RelativeSource TemplatedParent}}\">" fn)
  (write-line "                <ToggleButton.Template>" fn)
  (write-line "                  <ControlTemplate TargetType=\"ToggleButton\">" fn)
  (write-line "                    <Border x:Name=\"bd\" Background=\"#FFFFFF\" BorderBrush=\"#D0D5DD\" BorderThickness=\"1\" CornerRadius=\"8\">" fn)
  (write-line "                      <Path x:Name=\"arrow\" HorizontalAlignment=\"Right\" VerticalAlignment=\"Center\" Margin=\"0,0,14,0\" Data=\"M 0 0 L 5 5 L 10 0\" Stroke=\"#667085\" StrokeThickness=\"1.6\"/>" fn)
  (write-line "                    </Border>" fn)
  (write-line "                    <ControlTemplate.Triggers>" fn)
  (write-line "                      <Trigger Property=\"IsMouseOver\" Value=\"True\"><Setter TargetName=\"bd\" Property=\"BorderBrush\" Value=\"#98A2B3\"/></Trigger>" fn)
  (write-line "                      <Trigger Property=\"IsChecked\" Value=\"True\">" fn)
  (write-line "                        <Setter TargetName=\"bd\" Property=\"BorderBrush\" Value=\"#2563EB\"/>" fn)
  (write-line "                        <Setter TargetName=\"bd\" Property=\"BorderThickness\" Value=\"2\"/>" fn)
  (write-line "                        <Setter TargetName=\"arrow\" Property=\"Stroke\" Value=\"#2563EB\"/>" fn)
  (write-line "                      </Trigger>" fn)
  (write-line "                    </ControlTemplate.Triggers>" fn)
  (write-line "                  </ControlTemplate>" fn)
  (write-line "                </ToggleButton.Template>" fn)
  (write-line "              </ToggleButton>" fn)
  (write-line "              <ContentPresenter IsHitTestVisible=\"False\" Margin=\"14,0,36,0\" VerticalAlignment=\"Center\" HorizontalAlignment=\"Left\" Content=\"{TemplateBinding SelectionBoxItem}\" ContentTemplate=\"{TemplateBinding SelectionBoxItemTemplate}\"/>" fn)
  (write-line "              <Popup x:Name=\"PART_Popup\" Placement=\"Bottom\" IsOpen=\"{TemplateBinding IsDropDownOpen}\" AllowsTransparency=\"True\" Focusable=\"False\" PopupAnimation=\"Fade\">" fn)
  (write-line "                <Grid MinWidth=\"{Binding Path=ActualWidth, RelativeSource={RelativeSource TemplatedParent}}\" MaxHeight=\"280\" Margin=\"0,4,0,14\">" fn)
  (write-line "                  <Border Background=\"#FFFFFF\" BorderBrush=\"#E4E7EC\" BorderThickness=\"1\" CornerRadius=\"10\" Padding=\"4\">" fn)
  (write-line "                    <Border.Effect><DropShadowEffect BlurRadius=\"12\" ShadowDepth=\"3\" Opacity=\"0.22\" Color=\"#101828\"/></Border.Effect>" fn)
  (write-line "                    <ScrollViewer VerticalScrollBarVisibility=\"Auto\"><ItemsPresenter/></ScrollViewer>" fn)
  (write-line "                  </Border>" fn)
  (write-line "                </Grid>" fn)
  (write-line "              </Popup>" fn)
  (write-line "            </Grid>" fn)
  (write-line "          </ControlTemplate>" fn)
  (write-line "        </Setter.Value>" fn)
  (write-line "      </Setter>" fn)
  (write-line "    </Style>" fn)
  (write-line "  </Window.Resources>" fn)
  (write-line "  <Grid x:Name=\"RootGrid\">" fn)
  (write-line "    <Grid.RowDefinitions>" fn)
  (write-line "      <RowDefinition Height=\"Auto\"/>" fn)
  (write-line "      <RowDefinition Height=\"*\"/>" fn)
  (write-line "      <RowDefinition Height=\"Auto\"/>" fn)
  (write-line "    </Grid.RowDefinitions>" fn)
  (write-line "    <Border Grid.Row=\"0\" Background=\"#FFFFFF\" BorderBrush=\"#E4E7EC\" BorderThickness=\"0,0,0,1\" Padding=\"22,14\">" fn)
  (write-line "      <Grid>" fn)
  (write-line "        <Grid.ColumnDefinitions>" fn)
  (write-line "          <ColumnDefinition Width=\"*\"/>" fn)
  (write-line "          <ColumnDefinition Width=\"Auto\"/>" fn)
  (write-line "        </Grid.ColumnDefinitions>" fn)
  (write-line "        <StackPanel>" fn)
  (write-line "          <TextBlock Text=\"ブロック内部一括編集\" FontSize=\"18\" FontWeight=\"SemiBold\" Foreground=\"#101828\"/>" fn)
  (write-line "          <TextBlock x:Name=\"NamesText\" FontSize=\"12\" Foreground=\"#667085\" Margin=\"0,3,0,0\" TextTrimming=\"CharacterEllipsis\"/>" fn)
  (write-line "        </StackPanel>" fn)
  (write-line "        <WrapPanel x:Name=\"StatsPanel\" Grid.Column=\"1\" VerticalAlignment=\"Center\" Margin=\"16,0,0,0\"/>" fn)
  (write-line "      </Grid>" fn)
  (write-line "    </Border>" fn)
  (write-line "    <Grid Grid.Row=\"1\" Margin=\"16,14,16,0\">" fn)
  (write-line "      <Grid.ColumnDefinitions>" fn)
  (write-line "        <ColumnDefinition Width=\"*\" MinWidth=\"250\"/>" fn)
  (write-line "        <ColumnDefinition Width=\"12\"/>" fn)
  (write-line "        <ColumnDefinition Width=\"440\"/>" fn)
  (write-line "        <ColumnDefinition Width=\"12\"/>" fn)
  (write-line "        <ColumnDefinition Width=\"*\" MinWidth=\"320\"/>" fn)
  (write-line "      </Grid.ColumnDefinitions>" fn)
  (write-line "      <Grid x:Name=\"Col1\" Grid.Column=\"0\">" fn)
  (write-line "        <Grid.RowDefinitions>" fn)
  (write-line "          <RowDefinition Height=\"*\"/>" fn)
  (write-line "          <RowDefinition Height=\"12\"/>" fn)
  (write-line "          <RowDefinition Height=\"Auto\"/>" fn)
  (write-line "        </Grid.RowDefinitions>" fn)
  (write-line "        <Border Grid.Row=\"0\" Style=\"{StaticResource Card}\">" fn)
  (write-line "          <DockPanel>" fn)
  (write-line "            <StackPanel DockPanel.Dock=\"Top\">" fn)
  (write-line "<StackPanel Orientation=\"Horizontal\">" fn)
  (write-line "  <TextBlock Text=\"画層\" Style=\"{StaticResource CardTitle}\"/>" fn)
  (write-line "  <Border x:Name=\"BadgeLayer\" Visibility=\"Collapsed\" Background=\"#2563EB\" CornerRadius=\"9\" Padding=\"8,1,8,2\" Margin=\"8,0,0,0\" VerticalAlignment=\"Center\"><TextBlock Text=\"変更あり\" FontSize=\"11\" Foreground=\"#FFFFFF\"/></Border>" fn)
  (write-line "</StackPanel>" fn)
  (write-line "              <TextBlock x:Name=\"CurLayers\" Style=\"{StaticResource CardSub}\"/>" fn)
  (write-line "              <Border Margin=\"0,10,0,6\" Background=\"#F9FAFB\" BorderBrush=\"#D0D5DD\" BorderThickness=\"1\" CornerRadius=\"6\">" fn)
  (write-line "                <Grid>" fn)
  (write-line "                  <TextBlock x:Name=\"LayerHint\" Text=\"画層名で絞り込み\" Foreground=\"#98A2B3\" Margin=\"10,0\" VerticalAlignment=\"Center\" IsHitTestVisible=\"False\"/>" fn)
  (write-line "                  <TextBox x:Name=\"LayerSearch\" Background=\"Transparent\" BorderThickness=\"0\" Padding=\"7,6\" VerticalContentAlignment=\"Center\" Foreground=\"#101828\"/>" fn)
  (write-line "                </Grid>" fn)
  (write-line "              </Border>" fn)
  (write-line "            </StackPanel>" fn)
  (write-line "            <ListBox x:Name=\"LayerList\"/>" fn)
  (write-line "          </DockPanel>" fn)
  (write-line "        </Border>" fn)
  (write-line "        <Border Grid.Row=\"2\" Style=\"{StaticResource Card}\">" fn)
  (write-line "            <StackPanel>" fn)
  (write-line "<StackPanel Orientation=\"Horizontal\">" fn)
  (write-line "  <TextBlock Text=\"線種の置き換え\" Style=\"{StaticResource CardTitle}\"/>" fn)
  (write-line "  <Border x:Name=\"BadgeMap\" Visibility=\"Collapsed\" Background=\"#2563EB\" CornerRadius=\"9\" Padding=\"8,1,8,2\" Margin=\"8,0,0,0\" VerticalAlignment=\"Center\"><TextBlock Text=\"変更あり\" FontSize=\"11\" Foreground=\"#FFFFFF\"/></Border>" fn)
  (write-line "</StackPanel>" fn)
  (write-line "              <TextBlock Text=\"変更前の線種を選び、変更後の線種を選んで「追加」。例: A,B → A　C,D → F\" Style=\"{StaticResource CardSub}\" TextWrapping=\"Wrap\"/>" fn)
  (write-line "              <TextBlock Text=\"変更前（複数選択可）\" FontSize=\"12\" Foreground=\"#667085\" Margin=\"0,10,0,6\"/>" fn)
  (write-line "              <WrapPanel x:Name=\"MapSrcPanel\"/>" fn)
  (write-line "              <TextBlock Text=\"変更後\" FontSize=\"12\" Foreground=\"#667085\" Margin=\"2,12,0,5\"/>" fn)
  (write-line "              <Grid>" fn)
  (write-line "                <Grid.ColumnDefinitions>" fn)
  (write-line "                  <ColumnDefinition Width=\"*\"/>" fn)
  (write-line "                  <ColumnDefinition Width=\"Auto\"/>" fn)
  (write-line "                </Grid.ColumnDefinitions>" fn)
  (write-line "                <ComboBox x:Name=\"MapDst\" Style=\"{StaticResource MatCombo}\" Height=\"38\"/>" fn)
  (write-line "                <Button x:Name=\"MapAddBtn\" Grid.Column=\"1\" Content=\"追加\" Style=\"{StaticResource Primary}\" Height=\"38\" MinWidth=\"76\" Padding=\"16,0\" Margin=\"10,0,0,0\"/>" fn)
  (write-line "              </Grid>" fn)
  (write-line "              <StackPanel x:Name=\"MapRules\" Margin=\"0,10,0,0\"/>" fn)
  (write-line "            </StackPanel>" fn)
  (write-line "          </Border>" fn)
  (write-line "      </Grid>" fn)
  (write-line "      <ScrollViewer x:Name=\"Col2\" Grid.Column=\"2\" VerticalScrollBarVisibility=\"Auto\">" fn)
  (write-line "        <StackPanel>" fn)
  (write-line "          <Border Style=\"{StaticResource Card}\">" fn)
  (write-line "            <StackPanel>" fn)
  (write-line "<StackPanel Orientation=\"Horizontal\">" fn)
  (write-line "  <TextBlock Text=\"色\" Style=\"{StaticResource CardTitle}\"/>" fn)
  (write-line "  <Border x:Name=\"BadgeColor\" Visibility=\"Collapsed\" Background=\"#2563EB\" CornerRadius=\"9\" Padding=\"8,1,8,2\" Margin=\"8,0,0,0\" VerticalAlignment=\"Center\"><TextBlock Text=\"変更あり\" FontSize=\"11\" Foreground=\"#FFFFFF\"/></Border>" fn)
  (write-line "</StackPanel>" fn)
  (write-line "              <TextBlock x:Name=\"CurColors\" Style=\"{StaticResource CardSub}\"/>" fn)
  (write-line "              <WrapPanel x:Name=\"ColorQuick\" Margin=\"0,10,0,2\"/>" fn)
  (write-line "              <WrapPanel x:Name=\"ColorStd\" Margin=\"0,2,0,8\"/>" fn)
  (write-line "              <Grid Margin=\"0,4,0,0\">" fn)
  (write-line "                <Grid.ColumnDefinitions>" fn)
  (write-line "                  <ColumnDefinition Width=\"Auto\"/>" fn)
  (write-line "                  <ColumnDefinition Width=\"*\"/>" fn)
  (write-line "                  <ColumnDefinition Width=\"Auto\"/>" fn)
  (write-line "                </Grid.ColumnDefinitions>" fn)
  (write-line "                <Border x:Name=\"ColorPreview\" Width=\"22\" Height=\"22\" CornerRadius=\"5\" BorderBrush=\"#D0D5DD\" BorderThickness=\"1\"/>" fn)
  (write-line "                <TextBlock x:Name=\"ColorLabel\" Grid.Column=\"1\" Margin=\"10,0\" VerticalAlignment=\"Center\" FontWeight=\"SemiBold\" Foreground=\"#101828\"/>" fn)
  (write-line "                <Button x:Name=\"ColorDetailBtn\" Grid.Column=\"2\" Style=\"{StaticResource Chip}\" Margin=\"0\" Content=\"詳細な色番号\"/>" fn)
  (write-line "              </Grid>" fn)
  (write-line "              <StackPanel x:Name=\"ColorDetail\" Margin=\"0,12,0,0\" Visibility=\"Collapsed\">" fn)
  (write-line "              <UniformGrid x:Name=\"ColorGrid\" Columns=\"24\" Rows=\"10\" HorizontalAlignment=\"Left\"/>" fn)
  (write-line "                <StackPanel Orientation=\"Horizontal\" Margin=\"0,10,0,0\">" fn)
  (write-line "                  <TextBlock Text=\"番号\" Foreground=\"#667085\" FontSize=\"12\" VerticalAlignment=\"Center\" Margin=\"0,0,6,0\"/>" fn)
  (write-line "                  <Border x:Name=\"ColorNumBox\" Background=\"#F9FAFB\" BorderBrush=\"#D0D5DD\" BorderThickness=\"1\" CornerRadius=\"6\">" fn)
  (write-line "                    <TextBox x:Name=\"ColorNum\" Width=\"56\" Background=\"Transparent\" BorderThickness=\"0\" Padding=\"6,3\" ToolTip=\"1～255 を入力して Enter\"/>" fn)
  (write-line "                  </Border>" fn)
  (write-line "                </StackPanel>" fn)
  (write-line "              </StackPanel>" fn)
  (write-line "            </StackPanel>" fn)
  (write-line "          </Border>" fn)
  (write-line "          <Border Style=\"{StaticResource Card}\" Margin=\"0,12,0,0\">" fn)
  (write-line "            <StackPanel>" fn)
  (write-line "<StackPanel Orientation=\"Horizontal\">" fn)
  (write-line "  <TextBlock Text=\"線の太さ\" Style=\"{StaticResource CardTitle}\"/>" fn)
  (write-line "  <Border x:Name=\"BadgeLw\" Visibility=\"Collapsed\" Background=\"#2563EB\" CornerRadius=\"9\" Padding=\"8,1,8,2\" Margin=\"8,0,0,0\" VerticalAlignment=\"Center\"><TextBlock Text=\"変更あり\" FontSize=\"11\" Foreground=\"#FFFFFF\"/></Border>" fn)
  (write-line "</StackPanel>" fn)
  (write-line "              <TextBlock x:Name=\"CurLwts\" Style=\"{StaticResource CardSub}\"/>" fn)
  (write-line "              <TextBlock Text=\"mm単位で入力（例: 0.25）。最も近い標準の太さになります。空欄は変更しません。\" Style=\"{StaticResource CardSub}\" TextWrapping=\"Wrap\"/>" fn)
  (write-line "              <WrapPanel x:Name=\"LwQuick\" Margin=\"0,10,0,0\"/>" fn)
  (write-line "              <StackPanel Orientation=\"Horizontal\" Margin=\"0,4,0,0\">" fn)
  (write-line "                <Border x:Name=\"LwNumBox\" Background=\"#F9FAFB\" BorderBrush=\"#D0D5DD\" BorderThickness=\"1\" CornerRadius=\"6\">" fn)
  (write-line "                  <TextBox x:Name=\"LwNum\" Width=\"72\" Background=\"Transparent\" BorderThickness=\"0\" Padding=\"6,3\" ToolTip=\"0～2.11 の数値（mm）\"/>" fn)
  (write-line "                </Border>" fn)
  (write-line "                <TextBlock Text=\"mm\" Foreground=\"#667085\" FontSize=\"12\" VerticalAlignment=\"Center\" Margin=\"6,0,0,0\"/>" fn)
  (write-line "              </StackPanel>" fn)
  (write-line "            </StackPanel>" fn)
  (write-line "          </Border>" fn)
  (write-line "          <Border Style=\"{StaticResource Card}\" Margin=\"0,12,0,0\">" fn)
  (write-line "            <StackPanel>" fn)
  (write-line "<StackPanel Orientation=\"Horizontal\">" fn)
  (write-line "  <TextBlock Text=\"線種尺度\" Style=\"{StaticResource CardTitle}\"/>" fn)
  (write-line "  <Border x:Name=\"BadgeLtsc\" Visibility=\"Collapsed\" Background=\"#2563EB\" CornerRadius=\"9\" Padding=\"8,1,8,2\" Margin=\"8,0,0,0\" VerticalAlignment=\"Center\"><TextBlock Text=\"変更あり\" FontSize=\"11\" Foreground=\"#FFFFFF\"/></Border>" fn)
  (write-line "</StackPanel>" fn)
  (write-line "              <TextBlock x:Name=\"CurLtscales\" Style=\"{StaticResource CardSub}\"/>" fn)
  (write-line "              <WrapPanel x:Name=\"LtscQuick\" Margin=\"0,10,0,2\"/>" fn)
  (write-line "              <StackPanel Orientation=\"Horizontal\" Margin=\"0,4,0,0\">" fn)
  (write-line "                <TextBlock Text=\"値\" Foreground=\"#667085\" FontSize=\"12\" VerticalAlignment=\"Center\" Margin=\"0,0,6,0\"/>" fn)
  (write-line "                <Border x:Name=\"LtscNumBox\" Background=\"#F9FAFB\" BorderBrush=\"#D0D5DD\" BorderThickness=\"1\" CornerRadius=\"6\">" fn)
  (write-line "                  <TextBox x:Name=\"LtscNum\" Width=\"72\" Background=\"Transparent\" BorderThickness=\"0\" Padding=\"6,3\" ToolTip=\"0より大きい数値を入力（例: 0.5）\"/>" fn)
  (write-line "                </Border>" fn)
  (write-line "              </StackPanel>" fn)
  (write-line "              <Border Height=\"1\" Background=\"#EAECF0\" Margin=\"0,12,0,10\"/>" fn)
  (write-line "              <TextBlock Text=\"変更する範囲\" FontWeight=\"SemiBold\" Foreground=\"#344054\"/>" fn)
  (write-line "              <WrapPanel x:Name=\"LtscModePanel\" Margin=\"0,8,0,0\"/>" fn)
  (write-line "              <StackPanel x:Name=\"LtscTypeBox\" Visibility=\"Collapsed\">" fn)
  (write-line "                <TextBlock Text=\"尺度を変更する線種（複数選択可）\" Style=\"{StaticResource CardSub}\"/>" fn)
  (write-line "                <WrapPanel x:Name=\"LtscTypePanel\" Margin=\"0,8,0,0\"/>" fn)
  (write-line "              </StackPanel>" fn)
  (write-line "            </StackPanel>" fn)
  (write-line "          </Border>" fn)
  (write-line "        </StackPanel>" fn)
  (write-line "      </ScrollViewer>" fn)
  (write-line "      <Grid x:Name=\"Col3\" Grid.Column=\"4\">" fn)
  (write-line "        <Grid.RowDefinitions>" fn)
  (write-line "          <RowDefinition Height=\"Auto\"/>" fn)
  (write-line "          <RowDefinition Height=\"12\"/>" fn)
  (write-line "          <RowDefinition Height=\"*\"/>" fn)
  (write-line "        </Grid.RowDefinitions>" fn)
  (write-line "        <Border Grid.Row=\"0\" Style=\"{StaticResource Card}\">" fn)
  (write-line "          <StackPanel>" fn)
  (write-line "            <TextBlock Text=\"ハッチング・ソリッド\" Style=\"{StaticResource CardTitle}\"/>" fn)
  (write-line "            <TextBlock Text=\"ブロック内のハッチングや2Dソリッドを分解・削除します\" Style=\"{StaticResource CardSub}\"/>" fn)
  (write-line "            <StackPanel x:Name=\"HsPanel\" Margin=\"0,12,0,0\"/>" fn)
  (write-line "            <Border Background=\"#F9FAFB\" CornerRadius=\"6\" Padding=\"10,8\">" fn)
  (write-line "              <TextBlock TextWrapping=\"Wrap\" FontSize=\"12\" Foreground=\"#475467\"" fn)
  (write-line "                         Text=\"分解：塗りつぶし・模様を消して、輪郭線（ポリライン）に置き換えます。輪郭線は元の画層・色・線種を引き継ぎます。\"/>" fn)
  (write-line "            </Border>" fn)
  (write-line "            <StackPanel x:Name=\"ScopeBox\">" fn)
  (write-line "              <Border Height=\"1\" Background=\"#EAECF0\" Margin=\"0,14,0,12\"/>" fn)
  (write-line "              <TextBlock Text=\"プロパティ変更の適用先\" FontWeight=\"SemiBold\" Foreground=\"#344054\"/>" fn)
  (write-line "              <TextBlock Text=\"画層・線種・線種尺度・色・線の太さを変更する図形\" Style=\"{StaticResource CardSub}\"/>" fn)
  (write-line "              <WrapPanel x:Name=\"ScopePanel\" Margin=\"0,8,0,0\"/>" fn)
  (write-line "            </StackPanel>" fn)
  (write-line "          </StackPanel>" fn)
  (write-line "        </Border>" fn)
  (write-line "        <Border Grid.Row=\"2\" Style=\"{StaticResource Card}\">" fn)
  (write-line "          <DockPanel>" fn)
  (write-line "            <TextBlock DockPanel.Dock=\"Top\" Text=\"変更内容\" Style=\"{StaticResource CardTitle}\"/>" fn)
  (write-line "            <ScrollViewer VerticalScrollBarVisibility=\"Auto\" Margin=\"0,8,0,0\">" fn)
  (write-line "              <StackPanel x:Name=\"SummaryPanel\"/>" fn)
  (write-line "            </ScrollViewer>" fn)
  (write-line "          </DockPanel>" fn)
  (write-line "        </Border>" fn)
  (write-line "      </Grid>" fn)
  (write-line "    </Grid>" fn)
  (write-line "    <Border Grid.Row=\"2\" Margin=\"0,14,0,0\" Background=\"#FFFFFF\" BorderBrush=\"#E4E7EC\" BorderThickness=\"0,1,0,0\" Padding=\"22,12\">" fn)
  (write-line "      <Grid>" fn)
  (write-line "        <TextBlock Text=\"Enter：適用　　Esc：キャンセル\" Foreground=\"#98A2B3\" FontSize=\"12\" VerticalAlignment=\"Center\"/>" fn)
  (write-line "        <StackPanel Orientation=\"Horizontal\" HorizontalAlignment=\"Right\">" fn)
  (write-line "          <Button x:Name=\"CancelBtn\" Content=\"キャンセル\" Style=\"{StaticResource Btn}\"/>" fn)
  (write-line "          <Button x:Name=\"ApplyBtn\" Content=\"適用\" Style=\"{StaticResource Primary}\" Margin=\"10,0,0,0\"/>" fn)
  (write-line "        </StackPanel>" fn)
  (write-line "      </Grid>" fn)
  (write-line "    </Border>" fn)
  (write-line "  </Grid>" fn)
  (write-line "</Window>" fn)
  (write-line "'@" fn)
  (write-line "" fn)
  (write-line "$reader = New-Object System.Xml.XmlNodeReader ([xml]$xaml)" fn)
  (write-line "$window = [Windows.Markup.XamlReader]::Load($reader)" fn)
  (write-line "foreach ($n in 'RootGrid','NamesText','StatsPanel','Col1','Col2','Col3','CurLayers','LayerHint','LayerSearch','LayerList'," fn)
  (write-line "               'CurColors','ColorQuick','ColorStd','ColorGrid','ColorPreview','ColorLabel','ColorNumBox','ColorNum','ColorDetail','ColorDetailBtn'," fn)
  (write-line "               'CurLwts','LwQuick','LwNumBox','LwNum','CurLtscales','LtscQuick','LtscNumBox','LtscNum','LtscModePanel','LtscTypeBox','LtscTypePanel','BadgeLayer','BadgeColor','BadgeLw','BadgeLtsc','BadgeMap','MapSrcPanel','MapDst','MapAddBtn','MapRules','HsPanel','ScopeBox','ScopePanel','SummaryPanel','CancelBtn','ApplyBtn') {" fn)
  (write-line "    Set-Variable -Name $n -Value $window.FindName($n) -Scope Script" fn)
  (write-line "}" fn)
  (write-line "" fn)
  (write-line "$bc = New-Object System.Windows.Media.BrushConverter" fn)
  (write-line "function Br ($hex) { return $bc.ConvertFromString($hex) }" fn)
  (write-line "$chipStyle = $window.FindResource('Chip')" fn)
  (write-line "$swatchStyle = $window.FindResource('Swatch')" fn)
  (write-line "" fn)
  (write-line "function New-Text ($text, $size, $hex, $bold) {" fn)
  (write-line "    $t = New-Object System.Windows.Controls.TextBlock" fn)
  (write-line "    $t.Text = $text" fn)
  (write-line "    $t.FontSize = $size" fn)
  (write-line "    $t.Foreground = Br $hex" fn)
  (write-line "    if ($bold) { $t.FontWeight = [System.Windows.FontWeights]::SemiBold }" fn)
  (write-line "    $t.VerticalAlignment = [System.Windows.VerticalAlignment]::Center" fn)
  (write-line "    return $t" fn)
  (write-line "}" fn)
  (write-line "" fn)
  (write-line "function New-Badge ($text, $bg, $fg) {" fn)
  (write-line "    $b = New-Object System.Windows.Controls.Border" fn)
  (write-line "    $b.Background = Br $bg" fn)
  (write-line "    $b.CornerRadius = New-Object System.Windows.CornerRadius(10)" fn)
  (write-line "    $b.Padding = New-Object System.Windows.Thickness(8,1,8,2)" fn)
  (write-line "    $b.VerticalAlignment = [System.Windows.VerticalAlignment]::Center" fn)
  (write-line "    $b.Child = New-Text $text 11 $fg $false" fn)
  (write-line "    return $b" fn)
  (write-line "}" fn)
  (write-line "" fn)
  (write-line "function New-Chip ($panel, $text, $uid, [scriptblock]$handler) {" fn)
  (write-line "    $b = New-Object System.Windows.Controls.Button" fn)
  (write-line "    $b.Style = $chipStyle" fn)
  (write-line "    $b.Content = $text" fn)
  (write-line "    $b.Uid = $uid" fn)
  (write-line "    $b.Add_Click($handler)" fn)
  (write-line "    [void]$panel.Children.Add($b)" fn)
  (write-line "    return $b" fn)
  (write-line "}" fn)
  (write-line "" fn)
  (write-line "function Set-ActiveChip ($panel, $key, $tag) {" fn)
  (write-line "    foreach ($c in $panel.Children) {" fn)
  (write-line "        if ($c -is [System.Windows.Controls.Button]) {" fn)
  (write-line "            if ($c.Uid -eq $key) { $c.Tag = $tag } else { $c.Tag = $null }" fn)
  (write-line "        }" fn)
  (write-line "    }" fn)
  (write-line "}" fn)
  (write-line "" fn)
  (write-line "function Format-Current ($arr) {" fn)
  (write-line "    if ($arr -and $arr.Count -gt 0) { return '使用中: ' + ($arr -join ', ') }" fn)
  (write-line "    return '使用中: (なし)'" fn)
  (write-line "}" fn)
  (write-line "" fn)
  (write-line "# ---------- ヘッダー ----------" fn)
  (write-line "$names = @($inputData.Names)" fn)
  (write-line "if ($names.Count -gt 0) {" fn)
  (write-line "    $NamesText.Text = '対象: ' + ($names -join '、')" fn)
  (write-line "    $NamesText.ToolTip = ($names -join [Environment]::NewLine)" fn)
  (write-line "}" fn)
  (write-line "function Add-Stat ($label, $value) {" fn)
  (write-line "    $b = New-Object System.Windows.Controls.Border" fn)
  (write-line "    $b.Background = Br '#F2F4F7'" fn)
  (write-line "    $b.CornerRadius = New-Object System.Windows.CornerRadius(12)" fn)
  (write-line "    $b.Padding = New-Object System.Windows.Thickness(10,4,10,5)" fn)
  (write-line "    $b.Margin = New-Object System.Windows.Thickness(6,0,0,0)" fn)
  (write-line "    $sp = New-Object System.Windows.Controls.StackPanel" fn)
  (write-line "    $sp.Orientation = [System.Windows.Controls.Orientation]::Horizontal" fn)
  (write-line "    [void]$sp.Children.Add((New-Text $label 12 '#667085' $false))" fn)
  (write-line "    $v = New-Text $value 12 '#101828' $true" fn)
  (write-line "    $v.Margin = New-Object System.Windows.Thickness(6,0,0,0)" fn)
  (write-line "    [void]$sp.Children.Add($v)" fn)
  (write-line "    $b.Child = $sp" fn)
  (write-line "    [void]$StatsPanel.Children.Add($b)" fn)
  (write-line "}" fn)
  (write-line "$cntHatch = [int]$inputData.Hatch" fn)
  (write-line "$cntFill = [int]$inputData.Fill" fn)
  (write-line "$cntSolid = [int]$inputData.Solid" fn)
  (write-line "Add-Stat 'ブロック' \"$($inputData.BlkCount) 種類\"" fn)
  (write-line "Add-Stat '内部図形' \"$($inputData.EntCount)\"" fn)
  (write-line "if ($cntHatch -gt 0) { Add-Stat 'ハッチング' \"$cntHatch\" }" fn)
  (write-line "if ($cntFill -gt 0) { Add-Stat '塗りつぶし' \"$cntFill\" }" fn)
  (write-line "if ($cntSolid -gt 0) { Add-Stat 'ソリッド' \"$cntSolid\" }" fn)
  (write-line "" fn)
  (write-line "$CurLayers.Text = Format-Current $inputData.Layers" fn)
  (write-line "$CurLayers.ToolTip = $CurLayers.Text" fn)
  (write-line "$CurColors.Text = Format-Current $inputData.Colors" fn)
  (write-line "$CurLwts.Text = Format-Current $inputData.Lwts" fn)
  (write-line "$CurLtscales.Text = Format-Current $inputData.Ltscales" fn)
  (write-line "" fn)
  (write-line "# ---------- 一覧(画層・線種) ----------" fn)
  (write-line "function New-ListRow ($list, $value, $label, $rgb, $used) {" fn)
  (write-line "    $item = New-Object System.Windows.Controls.ListBoxItem" fn)
  (write-line "    $item.Tag = $value" fn)
  (write-line "    $dp = New-Object System.Windows.Controls.DockPanel" fn)
  (write-line "    if ($rgb) {" fn)
  (write-line "        $dot = New-Object System.Windows.Shapes.Rectangle" fn)
  (write-line "        $dot.Width = 12; $dot.Height = 12; $dot.RadiusX = 3; $dot.RadiusY = 3" fn)
  (write-line "        $dot.Fill = New-RgbBrush $rgb" fn)
  (write-line "        $dot.Stroke = Br '#40000000'" fn)
  (write-line "        $dot.Margin = New-Object System.Windows.Thickness(0,0,10,0)" fn)
  (write-line "        [System.Windows.Controls.DockPanel]::SetDock($dot, [System.Windows.Controls.Dock]::Left)" fn)
  (write-line "        [void]$dp.Children.Add($dot)" fn)
  (write-line "    }" fn)
  (write-line "    if ($used) {" fn)
  (write-line "        $badge = New-Badge '使用中' '#ECFDF3' '#067647'" fn)
  (write-line "        $badge.Margin = New-Object System.Windows.Thickness(8,0,0,0)" fn)
  (write-line "        [System.Windows.Controls.DockPanel]::SetDock($badge, [System.Windows.Controls.Dock]::Right)" fn)
  (write-line "        [void]$dp.Children.Add($badge)" fn)
  (write-line "    }" fn)
  (write-line "    if ($value -eq $NONE) { $tb = New-Text $label 13 '#667085' $false } else { $tb = New-Text $label 13 '#101828' $false }" fn)
  (write-line "    $tb.TextTrimming = [System.Windows.TextTrimming]::CharacterEllipsis" fn)
  (write-line "    $tb.ToolTip = $label" fn)
  (write-line "    [void]$dp.Children.Add($tb)" fn)
  (write-line "    $item.Content = $dp" fn)
  (write-line "    [void]$list.Items.Add($item)" fn)
  (write-line "}" fn)
  (write-line "" fn)
  (write-line "function Get-ListValue ($list) {" fn)
  (write-line "    $it = $list.SelectedItem" fn)
  (write-line "    if ($null -eq $it -or $it.Tag -eq $NONE) { return $null }" fn)
  (write-line "    return [string]$it.Tag" fn)
  (write-line "}" fn)
  (write-line "" fn)
  (write-line "$layerColor = @{}" fn)
  (write-line "foreach ($l in $inputData.AllLayers) {" fn)
  (write-line "    $p = $l.Split($TAB)" fn)
  (write-line "    $ci = 7" fn)
  (write-line "    if ($p.Count -gt 1) { [void][int]::TryParse($p[1], [ref]$ci) }" fn)
  (write-line "    $layerColor[$p[0]] = $ci" fn)
  (write-line "}" fn)
  (write-line "function Get-LayerRgb ($name) {" fn)
  (write-line "    if ($layerColor.ContainsKey($name)) { return Get-AciRgb $layerColor[$name] }" fn)
  (write-line "    return $null" fn)
  (write-line "}" fn)
  (write-line "" fn)
  (write-line "New-ListRow $LayerList $NONE '（変更しない）' $null $false" fn)
  (write-line "foreach ($n in (@($inputData.Layers) | Sort-Object)) { New-ListRow $LayerList $n $n (Get-LayerRgb $n) $true }" fn)
  (write-line "foreach ($n in (@($layerColor.Keys) | Sort-Object)) {" fn)
  (write-line "    if ($inputData.Layers -notcontains $n) { New-ListRow $LayerList $n $n (Get-LayerRgb $n) $false }" fn)
  (write-line "}" fn)
  (write-line "$LayerList.SelectedIndex = 0" fn)
  (write-line "" fn)
  (write-line "" fn)
  (write-line "$LayerSearch.Add_TextChanged({" fn)
  (write-line "    $q = $LayerSearch.Text.Trim()" fn)
  (write-line "    if ($q -eq '') { $LayerHint.Visibility = 'Visible' } else { $LayerHint.Visibility = 'Collapsed' }" fn)
  (write-line "    foreach ($it in $LayerList.Items) {" fn)
  (write-line "        $tag = [string]$it.Tag" fn)
  (write-line "        if ($q -eq '' -or $tag -eq $NONE -or $tag.IndexOf($q, [StringComparison]::OrdinalIgnoreCase) -ge 0) {" fn)
  (write-line "            $it.Visibility = 'Visible'" fn)
  (write-line "        } else {" fn)
  (write-line "            $it.Visibility = 'Collapsed'" fn)
  (write-line "        }" fn)
  (write-line "    }" fn)
  (write-line "})" fn)
  (write-line "" fn)
  (write-line "# ---------- 色 ----------" fn)
  (write-line "$script:color = $null" fn)
  (write-line "$aciNames = @{ '1' = '赤'; '2' = '黄'; '3' = '緑'; '4' = 'シアン'; '5' = '青'; '6' = 'マゼンタ'; '7' = '白/黒' }" fn)
  (write-line "function Get-ColorLabel ($val) {" fn)
  (write-line "    if ($null -eq $val) { return '変更しない' }" fn)
  (write-line "    if ($val -eq 'BYLAYER') { return 'ByLayer' }" fn)
  (write-line "    if ($val -eq 'BYBLOCK') { return 'ByBlock' }" fn)
  (write-line "    if ($aciNames.ContainsKey($val)) { return \"色 $val（$($aciNames[$val])）\" }" fn)
  (write-line "    return \"色 $val\"" fn)
  (write-line "}" fn)
  (write-line "" fn)
  (write-line "function Set-SelectedColor ($val) {" fn)
  (write-line "    $script:color = $val" fn)
  (write-line "    $key = $NONE" fn)
  (write-line "    if ($val) { $key = $val }" fn)
  (write-line "    Set-ActiveChip $ColorQuick $key 'sel'" fn)
  (write-line "    Set-ActiveChip $ColorStd $key 'sel'" fn)
  (write-line "    Set-ActiveChip $ColorGrid $key 'sel'" fn)
  (write-line "    $ColorLabel.Text = Get-ColorLabel $val" fn)
  (write-line "    if ($null -eq $val) {" fn)
  (write-line "        $ColorPreview.Background = Br '#00FFFFFF'" fn)
  (write-line "    } elseif ($val -eq 'BYLAYER' -or $val -eq 'BYBLOCK') {" fn)
  (write-line "        $ColorPreview.Background = Br '#E4E7EC'" fn)
  (write-line "    } else {" fn)
  (write-line "        $ColorPreview.Background = New-RgbBrush (Get-AciRgb ([int]$val))" fn)
  (write-line "    }" fn)
  (write-line "    Update-Summary" fn)
  (write-line "}" fn)
  (write-line "" fn)
  (write-line "function New-Swatch ($panel, [int]$idx, $size) {" fn)
  (write-line "    $sw = New-Object System.Windows.Controls.Button" fn)
  (write-line "    $sw.Style = $swatchStyle" fn)
  (write-line "    if ($size) { $sw.Width = $size; $sw.Height = $size; $sw.Margin = New-Object System.Windows.Thickness(0,0,4,0) }" fn)
  (write-line "    $sw.Uid = \"$idx\"" fn)
  (write-line "    $sw.ToolTip = Get-ColorLabel \"$idx\"" fn)
  (write-line "    $sw.Background = New-RgbBrush (Get-AciRgb $idx)" fn)
  (write-line "    $sw.Add_Click({ param($s, $e) Set-SelectedColor ([string]$s.Uid) })" fn)
  (write-line "    [void]$panel.Children.Add($sw)" fn)
  (write-line "}" fn)
  (write-line "" fn)
  (write-line "$colorChipClick = { param($s, $e) if ($s.Uid -eq $NONE) { Set-SelectedColor $null } else { Set-SelectedColor $s.Uid } }" fn)
  (write-line "[void](New-Chip $ColorQuick '変更しない' $NONE $colorChipClick)" fn)
  (write-line "[void](New-Chip $ColorQuick 'ByLayer' 'BYLAYER' $colorChipClick)" fn)
  (write-line "[void](New-Chip $ColorQuick 'ByBlock' 'BYBLOCK' $colorChipClick)" fn)
  (write-line "" fn)
  (write-line "foreach ($i in 1..9) { New-Swatch $ColorStd $i 21 }" fn)
  (write-line "$gap = New-Object System.Windows.Controls.Border" fn)
  (write-line "$gap.Width = 10" fn)
  (write-line "[void]$ColorStd.Children.Add($gap)" fn)
  (write-line "foreach ($i in 250..255) { New-Swatch $ColorStd $i 21 }" fn)
  (write-line "" fn)
  (write-line "foreach ($shade in @(0, 2, 4, 6, 8, 1, 3, 5, 7, 9)) {" fn)
  (write-line "    for ($c = 0; $c -lt 24; $c++) { New-Swatch $ColorGrid (10 + $c * 10 + $shade) $null }" fn)
  (write-line "}" fn)
  (write-line "" fn)
  (write-line "$ColorNum.Add_TextChanged({ $ColorNumBox.BorderBrush = Br '#D0D5DD' })" fn)
  (write-line "$ColorNum.Add_KeyDown({ param($s, $e)" fn)
  (write-line "    if ($e.Key -eq 'Return') {" fn)
  (write-line "        $n = 0" fn)
  (write-line "        if ([int]::TryParse($ColorNum.Text.Trim(), [ref]$n) -and $n -ge 1 -and $n -le 255) {" fn)
  (write-line "            Set-SelectedColor \"$n\"" fn)
  (write-line "        } else {" fn)
  (write-line "            $ColorNumBox.BorderBrush = Br '#F04438'" fn)
  (write-line "        }" fn)
  (write-line "        $e.Handled = $true" fn)
  (write-line "    }" fn)
  (write-line "})" fn)
  (write-line "" fn)
  (write-line "$script:colorDetailOpen = $false" fn)
  (write-line "function Set-ColorDetail ($show) {" fn)
  (write-line "    $script:colorDetailOpen = $show" fn)
  (write-line "    if ($show) {" fn)
  (write-line "        $ColorDetail.Visibility = 'Visible'" fn)
  (write-line "        $ColorDetailBtn.Content = '詳細な色番号 ' + [char]0x25B2" fn)
  (write-line "        $ColorDetailBtn.Tag = 'sel'" fn)
  (write-line "    } else {" fn)
  (write-line "        $ColorDetail.Visibility = 'Collapsed'" fn)
  (write-line "        $ColorDetailBtn.Content = '詳細な色番号 ' + [char]0x25BC" fn)
  (write-line "        $ColorDetailBtn.Tag = $null" fn)
  (write-line "    }" fn)
  (write-line "}" fn)
  (write-line "function Switch-ColorDetail { Set-ColorDetail (-not $script:colorDetailOpen) }" fn)
  (write-line "$ColorDetailBtn.Add_Click({ Switch-ColorDetail })" fn)
  (write-line "Set-ColorDetail $false" fn)
  (write-line "" fn)
  (write-line "# ---------- 線の太さ ----------" fn)
  (write-line "$script:lw = $null" fn)
  (write-line "$script:lwWord = $null" fn)
  (write-line "$lwStd = @(0, 5, 9, 13, 15, 18, 20, 25, 30, 35, 40, 50, 53, 60, 70, 80, 90, 100, 106, 120, 140, 158, 200, 211)" fn)
  (write-line "function Get-LwLabel ($val) {" fn)
  (write-line "    if ($null -eq $val) { return '変更しない' }" fn)
  (write-line "    switch ($val) {" fn)
  (write-line "        'BYLAYER' { return 'ByLayer' }" fn)
  (write-line "        'BYBLOCK' { return 'ByBlock' }" fn)
  (write-line "        'DEFAULT' { return '既定' }" fn)
  (write-line "    }" fn)
  (write-line "    return ('{0:0.00} mm' -f ([int]$val / 100.0))" fn)
  (write-line "}" fn)
  (write-line "function Update-LwText {" fn)
  (write-line "    $t = $LwNum.Text.Trim()" fn)
  (write-line "    $d = 0.0" fn)
  (write-line "    $script:lw = $null" fn)
  (write-line "    $LwNumBox.BorderBrush = Br '#D0D5DD'" fn)
  (write-line "    if ($t -ne '') {" fn)
  (write-line "        $script:lwWord = $null" fn)
  (write-line "        if ([double]::TryParse($t, [System.Globalization.NumberStyles]::Float, [System.Globalization.CultureInfo]::InvariantCulture, [ref]$d) -and $d -ge 0 -and $d -le 2.11) {" fn)
  (write-line "            $raw = $d * 100" fn)
  (write-line "            $near = $lwStd | Sort-Object { [math]::Abs($_ - $raw) } | Select-Object -First 1" fn)
  (write-line "            $script:lw = [string]$near" fn)
  (write-line "        } else {" fn)
  (write-line "            $LwNumBox.BorderBrush = Br '#F04438'" fn)
  (write-line "        }" fn)
  (write-line "    }" fn)
  (write-line "    if ($script:lwWord) { $script:lw = $script:lwWord }" fn)
  (write-line "    $key = '__numeric__'" fn)
  (write-line "    if ($script:lwWord) { $key = $script:lwWord } elseif ($t -eq '') { $key = $NONE }" fn)
  (write-line "    Set-ActiveChip $LwQuick $key 'sel'" fn)
  (write-line "    Update-Summary" fn)
  (write-line "}" fn)
  (write-line "function Set-LwWord ($w) {" fn)
  (write-line "    $script:lwWord = $w" fn)
  (write-line "    $LwNum.Text = ''" fn)
  (write-line "    Update-LwText" fn)
  (write-line "}" fn)
  (write-line "$lwClick = { param($s, $e) if ($s.Uid -eq $NONE) { Set-LwWord $null } else { Set-LwWord $s.Uid } }" fn)
  (write-line "[void](New-Chip $LwQuick '変更しない' $NONE $lwClick)" fn)
  (write-line "[void](New-Chip $LwQuick 'ByLayer' 'BYLAYER' $lwClick)" fn)
  (write-line "[void](New-Chip $LwQuick 'ByBlock' 'BYBLOCK' $lwClick)" fn)
  (write-line "[void](New-Chip $LwQuick '既定' 'DEFAULT' $lwClick)" fn)
  (write-line "$LwNum.Add_TextChanged({ Update-LwText })" fn)
  (write-line "" fn)
  (write-line "# ---------- 線種尺度 ----------" fn)
  (write-line "$script:ltsc = $null" fn)
  (write-line "$script:ltscMode = 'ALL'" fn)
  (write-line "$script:ltscTypes = @()" fn)
  (write-line "$ltscCulture = [System.Globalization.CultureInfo]::InvariantCulture" fn)
  (write-line "function Test-LtscEffective {" fn)
  (write-line "    if ($null -eq $script:ltsc) { return $false }" fn)
  (write-line "    if ($script:ltscMode -eq 'TYPE' -and @($script:ltscTypes).Count -eq 0) { return $false }" fn)
  (write-line "    return $true" fn)
  (write-line "}" fn)
  (write-line "function Update-LtscText {" fn)
  (write-line "    $t = $LtscNum.Text.Trim()" fn)
  (write-line "    $d = 0.0" fn)
  (write-line "    $script:ltsc = $null" fn)
  (write-line "    $LtscNumBox.BorderBrush = Br '#D0D5DD'" fn)
  (write-line "    if ($t -ne '') {" fn)
  (write-line "        if ([double]::TryParse($t, [System.Globalization.NumberStyles]::Float, $ltscCulture, [ref]$d) -and $d -ge 0.000001 -and $d -lt 1000000) {" fn)
  (write-line "            $script:ltsc = $d.ToString('0.######', $ltscCulture)" fn)
  (write-line "        } else {" fn)
  (write-line "            $LtscNumBox.BorderBrush = Br '#F04438'" fn)
  (write-line "        }" fn)
  (write-line "    }" fn)
  (write-line "    $key = $NONE" fn)
  (write-line "    if ($script:ltsc) { $key = $script:ltsc }" fn)
  (write-line "    Set-ActiveChip $LtscQuick $key 'sel'" fn)
  (write-line "    Update-Summary" fn)
  (write-line "}" fn)
  (write-line "$ltscQuickClick = { param($s, $e) if ($s.Uid -eq $NONE) { $LtscNum.Text = '' } else { $LtscNum.Text = $s.Uid } }" fn)
  (write-line "[void](New-Chip $LtscQuick '変更しない' $NONE $ltscQuickClick)" fn)
  (write-line "foreach ($v in '0.1', '0.5', '1', '2', '5', '10') { [void](New-Chip $LtscQuick $v $v $ltscQuickClick) }" fn)
  (write-line "$LtscNum.Add_TextChanged({ Update-LtscText })" fn)
  (write-line "" fn)
  (write-line "$ltscModeTitles = @{ ALL = 'すべての図形に一括'; TYPE = '選んだ線種の図形だけ' }" fn)
  (write-line "function Set-LtscMode ($val) {" fn)
  (write-line "    $script:ltscMode = $val" fn)
  (write-line "    Set-ActiveChip $LtscModePanel $val 'sel'" fn)
  (write-line "    if ($val -eq 'TYPE') { $LtscTypeBox.Visibility = 'Visible' } else { $LtscTypeBox.Visibility = 'Collapsed' }" fn)
  (write-line "    Update-Summary" fn)
  (write-line "}" fn)
  (write-line "$ltscModeClick = { param($s, $e) Set-LtscMode $s.Uid }" fn)
  (write-line "foreach ($k in 'ALL', 'TYPE') { [void](New-Chip $LtscModePanel $ltscModeTitles[$k] $k $ltscModeClick) }" fn)
  (write-line "" fn)
  (write-line "function Update-LtscTypeChips {" fn)
  (write-line "    foreach ($c in $LtscTypePanel.Children) {" fn)
  (write-line "        if (@($script:ltscTypes) -contains $c.Uid) { $c.Tag = 'sel' } else { $c.Tag = $null }" fn)
  (write-line "    }" fn)
  (write-line "}" fn)
  (write-line "function Switch-LtscType ($name) {" fn)
  (write-line "    if (@($script:ltscTypes) -contains $name) {" fn)
  (write-line "        $script:ltscTypes = @($script:ltscTypes | Where-Object { $_ -ne $name })" fn)
  (write-line "    } else {" fn)
  (write-line "        $script:ltscTypes = @($script:ltscTypes) + $name" fn)
  (write-line "    }" fn)
  (write-line "    Update-LtscTypeChips" fn)
  (write-line "    Update-Summary" fn)
  (write-line "}" fn)
  (write-line "$ltscTypeClick = { param($s, $e) Switch-LtscType $s.Uid }" fn)
  (write-line "$ltscNames = @()" fn)
  (write-line "foreach ($n in 'ByLayer', 'ByBlock') { if (@($inputData.Ltypes) -contains $n) { $ltscNames += $n } }" fn)
  (write-line "foreach ($n in (@($inputData.Ltypes) | Sort-Object)) { if ($ltscNames -notcontains $n) { $ltscNames += $n } }" fn)
  (write-line "foreach ($n in $ltscNames) { [void](New-Chip $LtscTypePanel $n $n $ltscTypeClick) }" fn)
  (write-line "" fn)
  (write-line "# ---------- 線種の置き換え ----------" fn)
  (write-line "$script:ltMap = @()" fn)
  (write-line "$script:mapSel = @()" fn)
  (write-line "function Update-MapChips {" fn)
  (write-line "    foreach ($c in $MapSrcPanel.Children) {" fn)
  (write-line "        if (@($script:mapSel) -contains $c.Uid) { $c.Tag = 'sel' } else { $c.Tag = $null }" fn)
  (write-line "    }" fn)
  (write-line "}" fn)
  (write-line "function Switch-MapSrc ($name) {" fn)
  (write-line "    if (@($script:mapSel) -contains $name) {" fn)
  (write-line "        $script:mapSel = @($script:mapSel | Where-Object { $_ -ne $name })" fn)
  (write-line "    } else {" fn)
  (write-line "        $script:mapSel = @($script:mapSel) + $name" fn)
  (write-line "    }" fn)
  (write-line "    Update-MapChips" fn)
  (write-line "}" fn)
  (write-line "$mapSrcClick = { param($s, $e) Switch-MapSrc $s.Uid }" fn)
  (write-line "foreach ($n in $ltscNames) { [void](New-Chip $MapSrcPanel $n $n $mapSrcClick) }" fn)
  (write-line "$mapDstNames = @('ByLayer', 'ByBlock')" fn)
  (write-line "foreach ($n in ((@($inputData.AllLtypes) + @($inputData.Ltypes)) | Sort-Object -Unique)) { if ($mapDstNames -notcontains $n) { $mapDstNames += $n } }" fn)
  (write-line "foreach ($n in $mapDstNames) { [void]$MapDst.Items.Add($n) }" fn)
  (write-line "$MapDst.SelectedIndex = 0" fn)
  (write-line "function Update-MapRules {" fn)
  (write-line "    $MapRules.Children.Clear()" fn)
  (write-line "    $i = 0" fn)
  (write-line "    foreach ($r in @($script:ltMap)) {" fn)
  (write-line "        $row = New-Object System.Windows.Controls.StackPanel" fn)
  (write-line "        $row.Orientation = [System.Windows.Controls.Orientation]::Horizontal" fn)
  (write-line "        $row.Margin = New-Object System.Windows.Thickness(0,0,0,4)" fn)
  (write-line "        [void]$row.Children.Add((New-Text ((@($r.Srcs) -join ', ') + '  ' + [char]0x2192 + '  ' + $r.Dst) 13 '#101828' $true))" fn)
  (write-line "        $b = New-Chip $row '削除' \"$i\" $mapDelClick" fn)
  (write-line "        $b.Tag = 'danger'" fn)
  (write-line "        $b.Margin = New-Object System.Windows.Thickness(10,0,0,0)" fn)
  (write-line "        [void]$MapRules.Children.Add($row)" fn)
  (write-line "        $i++" fn)
  (write-line "    }" fn)
  (write-line "}" fn)
  (write-line "function Remove-MapRule ([int]$idx) {" fn)
  (write-line "    $new = @()" fn)
  (write-line "    for ($i = 0; $i -lt @($script:ltMap).Count; $i++) { if ($i -ne $idx) { $new += $script:ltMap[$i] } }" fn)
  (write-line "    $script:ltMap = $new" fn)
  (write-line "    Update-MapRules" fn)
  (write-line "    Update-Summary" fn)
  (write-line "}" fn)
  (write-line "$mapDelClick = { param($s, $e) Remove-MapRule ([int]$s.Uid) }" fn)
  (write-line "function Add-MapRuleCore {" fn)
  (write-line "    if (@($script:mapSel).Count -eq 0 -or $null -eq $MapDst.SelectedItem) { return }" fn)
  (write-line "    $dst = [string]$MapDst.SelectedItem" fn)
  (write-line "    $sel = @($script:mapSel)" fn)
  (write-line "    $new = @()" fn)
  (write-line "    foreach ($r in @($script:ltMap)) {" fn)
  (write-line "        $rest = @($r.Srcs | Where-Object { $sel -notcontains $_ })" fn)
  (write-line "        if ($rest.Count -gt 0) { $new += @{ Dst = $r.Dst; Srcs = $rest } }" fn)
  (write-line "    }" fn)
  (write-line "    $new += @{ Dst = $dst; Srcs = $sel }" fn)
  (write-line "    $script:ltMap = $new" fn)
  (write-line "    $script:mapSel = @()" fn)
  (write-line "    Update-MapChips" fn)
  (write-line "    Update-MapRules" fn)
  (write-line "    Update-Summary" fn)
  (write-line "}" fn)
  (write-line "function Add-MapRule {" fn)
  (write-line "    try { Add-MapRuleCore } catch { [void][System.Windows.MessageBox]::Show('ルールの追加でエラー: ' + $_.Exception.Message) }" fn)
  (write-line "}" fn)
  (write-line "$MapAddBtn.Add_Click({ Add-MapRule })" fn)
  (write-line "" fn)
  (write-line "# ---------- ハッチング・ソリッド ----------" fn)
  (write-line "$script:hs = @{ HATCH = 'KEEP'; FILL = 'KEEP'; SOLID = 'KEEP' }" fn)
  (write-line "$hsTitles = @{ HATCH = 'パターンハッチング'; FILL = '塗りつぶしハッチング'; SOLID = '2Dソリッド' }" fn)
  (write-line "$hsPanels = @{}" fn)
  (write-line "function Set-HsAction ($kind, $act) {" fn)
  (write-line "    $script:hs[$kind] = $act" fn)
  (write-line "    $tag = 'sel'" fn)
  (write-line "    if ($act -eq 'DELETE') { $tag = 'danger' }" fn)
  (write-line "    Set-ActiveChip $hsPanels[$kind] \"${kind}:$act\" $tag" fn)
  (write-line "    Update-Summary" fn)
  (write-line "}" fn)
  (write-line "$hsClick = { param($s, $e) $p = $s.Uid.Split(':'); Set-HsAction $p[0] $p[1] }" fn)
  (write-line "function New-HsRow ($kind, $count) {" fn)
  (write-line "    $dp = New-Object System.Windows.Controls.DockPanel" fn)
  (write-line "    $dp.Margin = New-Object System.Windows.Thickness(0,0,0,8)" fn)
  (write-line "    $chips = New-Object System.Windows.Controls.WrapPanel" fn)
  (write-line "    [System.Windows.Controls.DockPanel]::SetDock($chips, [System.Windows.Controls.Dock]::Right)" fn)
  (write-line "    [void](New-Chip $chips 'そのまま' \"${kind}:KEEP\" $hsClick)" fn)
  (write-line "    [void](New-Chip $chips '分解' \"${kind}:EXPLODE\" $hsClick)" fn)
  (write-line "    [void](New-Chip $chips '削除' \"${kind}:DELETE\" $hsClick)" fn)
  (write-line "    [void]$dp.Children.Add($chips)" fn)
  (write-line "    $sp = New-Object System.Windows.Controls.StackPanel" fn)
  (write-line "    $sp.Orientation = [System.Windows.Controls.Orientation]::Horizontal" fn)
  (write-line "    $sp.VerticalAlignment = [System.Windows.VerticalAlignment]::Top" fn)
  (write-line "    $sp.Margin = New-Object System.Windows.Thickness(0,3,0,0)" fn)
  (write-line "    [void]$sp.Children.Add((New-Text $hsTitles[$kind] 13 '#344054' $true))" fn)
  (write-line "    if ($count -gt 0) { $badge = New-Badge \"$count\" '#EFF4FF' '#1D4ED8' } else { $badge = New-Badge 'なし' '#F2F4F7' '#667085' }" fn)
  (write-line "    $badge.Margin = New-Object System.Windows.Thickness(8,0,0,0)" fn)
  (write-line "    [void]$sp.Children.Add($badge)" fn)
  (write-line "    [void]$dp.Children.Add($sp)" fn)
  (write-line "    if ($count -le 0) { $chips.IsEnabled = $false; $chips.Opacity = 0.45 }" fn)
  (write-line "    [void]$HsPanel.Children.Add($dp)" fn)
  (write-line "    $hsPanels[$kind] = $chips" fn)
  (write-line "}" fn)
  (write-line "New-HsRow 'HATCH' $cntHatch" fn)
  (write-line "New-HsRow 'FILL' $cntFill" fn)
  (write-line "New-HsRow 'SOLID' $cntSolid" fn)
  (write-line "" fn)
  (write-line "$script:scope = 'ALL'" fn)
  (write-line "$scopeTitles = @{ ALL = 'すべての図形'; HS = 'ハッチング・ソリッドのみ'; OTHER = 'それ以外のみ' }" fn)
  (write-line "function Set-Scope ($val) {" fn)
  (write-line "    $script:scope = $val" fn)
  (write-line "    Set-ActiveChip $ScopePanel $val 'sel'" fn)
  (write-line "    Update-Summary" fn)
  (write-line "}" fn)
  (write-line "$scopeClick = { param($s, $e) Set-Scope $s.Uid }" fn)
  (write-line "foreach ($k in 'ALL', 'HS', 'OTHER') { [void](New-Chip $ScopePanel $scopeTitles[$k] $k $scopeClick) }" fn)
  (write-line "if (($cntHatch + $cntFill + $cntSolid) -le 0) { $ScopeBox.Visibility = 'Collapsed' }" fn)
  (write-line "" fn)
  (write-line "# ---------- 変更内容 ----------" fn)
  (write-line "function Add-SummaryRow ($label, $value, $danger) {" fn)
  (write-line "    $g = New-Object System.Windows.Controls.Grid" fn)
  (write-line "    $g.Margin = New-Object System.Windows.Thickness(0,0,0,8)" fn)
  (write-line "    $c0 = New-Object System.Windows.Controls.ColumnDefinition" fn)
  (write-line "    $c0.Width = New-Object System.Windows.GridLength(140)" fn)
  (write-line "    $c1 = New-Object System.Windows.Controls.ColumnDefinition" fn)
  (write-line "    [void]$g.ColumnDefinitions.Add($c0)" fn)
  (write-line "    [void]$g.ColumnDefinitions.Add($c1)" fn)
  (write-line "    $l = New-Text $label 12 '#667085' $false" fn)
  (write-line "    $l.VerticalAlignment = [System.Windows.VerticalAlignment]::Top" fn)
  (write-line "    $fg = '#101828'" fn)
  (write-line "    if ($danger) { $fg = '#B42318' }" fn)
  (write-line "    $v = New-Text ([char]0x2192 + ' ' + $value) 13 $fg $true" fn)
  (write-line "    $v.TextWrapping = [System.Windows.TextWrapping]::Wrap" fn)
  (write-line "    [System.Windows.Controls.Grid]::SetColumn($v, 1)" fn)
  (write-line "    [void]$g.Children.Add($l)" fn)
  (write-line "    [void]$g.Children.Add($v)" fn)
  (write-line "    [void]$SummaryPanel.Children.Add($g)" fn)
  (write-line "}" fn)
  (write-line "" fn)
  (write-line "$script:ready = $false" fn)
  (write-line "function Set-Badge ($el, $on) { if ($on) { $el.Visibility = 'Visible' } else { $el.Visibility = 'Collapsed' } }" fn)
  (write-line "function Update-Badges {" fn)
  (write-line "    Set-Badge $BadgeLayer ($null -ne (Get-ListValue $LayerList))" fn)
  (write-line "    Set-Badge $BadgeColor ($null -ne $script:color)" fn)
  (write-line "    Set-Badge $BadgeLw ($null -ne $script:lw)" fn)
  (write-line "    Set-Badge $BadgeLtsc (Test-LtscEffective)" fn)
  (write-line "    Set-Badge $BadgeMap (@($script:ltMap).Count -gt 0)" fn)
  (write-line "}" fn)
  (write-line "function Update-Summary {" fn)
  (write-line "    if (-not $script:ready) { return }" fn)
  (write-line "    $SummaryPanel.Children.Clear()" fn)
  (write-line "    $n = 0" fn)
  (write-line "    $v = Get-ListValue $LayerList" fn)
  (write-line "    if ($v) { Add-SummaryRow '画層' $v $false; $n++ }" fn)
  (write-line "    foreach ($r in @($script:ltMap)) { Add-SummaryRow '線種の置き換え' ((@($r.Srcs) -join ', ') + ' ' + [char]0x2192 + ' ' + $r.Dst) $false; $n++ }" fn)
  (write-line "    if ($script:color) { Add-SummaryRow '色' (Get-ColorLabel $script:color) $false; $n++ }" fn)
  (write-line "    if ($script:lw) { Add-SummaryRow '線の太さ' (Get-LwLabel $script:lw) $false; $n++ }" fn)
  (write-line "    if (Test-LtscEffective) {" fn)
  (write-line "        if ($script:ltscMode -eq 'TYPE') { $txt = $script:ltsc + '（' + (@($script:ltscTypes) -join ', ') + ' のみ）' } else { $txt = $script:ltsc + '（すべての図形）' }" fn)
  (write-line "        Add-SummaryRow '線種尺度' $txt $false" fn)
  (write-line "        $n++" fn)
  (write-line "    } elseif ($script:ltsc -and $script:ltscMode -eq 'TYPE') {" fn)
  (write-line "        Add-SummaryRow '線種尺度' '対象の線種を選んでください' $false" fn)
  (write-line "    }" fn)
  (write-line "    if ($n -gt 0 -and $script:scope -ne 'ALL') { Add-SummaryRow '適用先' $scopeTitles[$script:scope] $false }" fn)
  (write-line "    foreach ($k in 'HATCH', 'FILL', 'SOLID') {" fn)
  (write-line "        if ($script:hs[$k] -eq 'EXPLODE') { Add-SummaryRow $hsTitles[$k] '分解（輪郭線へ）' $false; $n++ }" fn)
  (write-line "        elseif ($script:hs[$k] -eq 'DELETE') { Add-SummaryRow $hsTitles[$k] '削除' $true; $n++ }" fn)
  (write-line "    }" fn)
  (write-line "    if ($n -eq 0) {" fn)
  (write-line "        $t = New-Text '変更する項目を選んでください。' 12 '#98A2B3' $false" fn)
  (write-line "        $t.TextWrapping = [System.Windows.TextWrapping]::Wrap" fn)
  (write-line "        [void]$SummaryPanel.Children.Add($t)" fn)
  (write-line "    }" fn)
  (write-line "    $ApplyBtn.IsEnabled = ($n -gt 0)" fn)
  (write-line "    Update-Badges" fn)
  (write-line "    if ($n -gt 0) { $ApplyBtn.Content = \"適用（${n}項目）\" } else { $ApplyBtn.Content = '適用' }" fn)
  (write-line "}" fn)
  (write-line "$LayerList.Add_SelectionChanged({ Update-Summary })" fn)
  (write-line "" fn)
  (write-line "# ---------- アニメーション ----------" fn)
  (write-line "function New-DoubleAnim ($from, $to, $ms, $delayMs) {" fn)
  (write-line "    $a = New-Object System.Windows.Media.Animation.DoubleAnimation" fn)
  (write-line "    if ($null -ne $from) { $a.From = [double]$from }" fn)
  (write-line "    $a.To = [double]$to" fn)
  (write-line "    $a.Duration = New-Object System.Windows.Duration ([TimeSpan]::FromMilliseconds($ms))" fn)
  (write-line "    if ($delayMs) { $a.BeginTime = [TimeSpan]::FromMilliseconds($delayMs) }" fn)
  (write-line "    $a.DecelerationRatio = 0.8" fn)
  (write-line "    return $a" fn)
  (write-line "}" fn)
  (write-line "function Start-Entrance {" fn)
  (write-line "    $delay = 0" fn)
  (write-line "    foreach ($el in @($Col1, $Col2, $Col3)) {" fn)
  (write-line "        try {" fn)
  (write-line "            $tt = New-Object System.Windows.Media.TranslateTransform" fn)
  (write-line "            $el.RenderTransform = $tt" fn)
  (write-line "            $el.Opacity = 0" fn)
  (write-line "            $el.BeginAnimation([System.Windows.UIElement]::OpacityProperty, (New-DoubleAnim 0 1 260 $delay))" fn)
  (write-line "            $tt.BeginAnimation([System.Windows.Media.TranslateTransform]::YProperty, (New-DoubleAnim 14 0 300 $delay))" fn)
  (write-line "        } catch {" fn)
  (write-line "            $el.BeginAnimation([System.Windows.UIElement]::OpacityProperty, $null)" fn)
  (write-line "            $el.Opacity = 1" fn)
  (write-line "        }" fn)
  (write-line "        $delay += 60" fn)
  (write-line "    }" fn)
  (write-line "}" fn)
  (write-line "$script:closing = $false" fn)
  (write-line "function Close-Animated ($tag) {" fn)
  (write-line "    if ($script:closing) { return }" fn)
  (write-line "    $script:closing = $true" fn)
  (write-line "    $window.Tag = $tag" fn)
  (write-line "    try {" fn)
  (write-line "        $a = New-DoubleAnim $null 0 130 0" fn)
  (write-line "        $a.Add_Completed({ $window.Close() })" fn)
  (write-line "        $RootGrid.BeginAnimation([System.Windows.UIElement]::OpacityProperty, $a)" fn)
  (write-line "    } catch {" fn)
  (write-line "        $window.Close()" fn)
  (write-line "    }" fn)
  (write-line "}" fn)
  (write-line "" fn)
  (write-line "$script:ready = $true" fn)
  (write-line "Set-SelectedColor $null" fn)
  (write-line "Update-LwText" fn)
  (write-line "Set-LtscMode 'ALL'" fn)
  (write-line "Update-LtscText" fn)
  (write-line "Set-HsAction 'HATCH' 'KEEP'" fn)
  (write-line "Set-HsAction 'FILL' 'KEEP'" fn)
  (write-line "Set-HsAction 'SOLID' 'KEEP'" fn)
  (write-line "Set-Scope 'ALL'" fn)
  (write-line "" fn)
  (write-line "$window.Tag = 'CANCEL'" fn)
  (write-line "$window.Add_Loaded({ Start-Entrance })" fn)
  (write-line "$ApplyBtn.Add_Click({ Close-Animated 'OK' })" fn)
  (write-line "$CancelBtn.Add_Click({ Close-Animated 'CANCEL' })" fn)
  (write-line "$window.Add_PreviewKeyDown({ param($s, $e)" fn)
  (write-line "    if ($e.Key -eq 'Escape') {" fn)
  (write-line "        Close-Animated 'CANCEL'" fn)
  (write-line "        $e.Handled = $true" fn)
  (write-line "    } elseif ($e.Key -eq 'Return' -and -not ([System.Windows.Input.Keyboard]::FocusedElement -is [System.Windows.Controls.TextBox])) {" fn)
  (write-line "        if ($ApplyBtn.IsEnabled) { Close-Animated 'OK' }" fn)
  (write-line "        $e.Handled = $true" fn)
  (write-line "    }" fn)
  (write-line "})" fn)
  (write-line "" fn)
  (write-line "[void]$window.ShowDialog()" fn)
  (write-line "" fn)
  (write-line "$result = @()" fn)
  (write-line "if ($window.Tag -eq 'OK') {" fn)
  (write-line "    $v = Get-ListValue $LayerList" fn)
  (write-line "    if ($v) { $result += \"LAYER=$v\" }" fn)
  (write-line "    foreach ($r in @($script:ltMap)) { $result += \"LTMAPDST=$($r.Dst)\"; foreach ($s in @($r.Srcs)) { $result += \"LTMAPSRC=$s\" } }" fn)
  (write-line "    if ($script:color) { $result += \"COLOR=$($script:color)\" }" fn)
  (write-line "    if ($script:lw) { $result += \"LWT=$($script:lw)\" }" fn)
  (write-line "    if (Test-LtscEffective) {" fn)
  (write-line "        $result += \"LTSCALE=$($script:ltsc)\"" fn)
  (write-line "        $result += \"LTSCALEMODE=$($script:ltscMode)\"" fn)
  (write-line "        if ($script:ltscMode -eq 'TYPE') { foreach ($t in @($script:ltscTypes)) { $result += \"LTSCALETYPE=$t\" } }" fn)
  (write-line "    }" fn)
  (write-line "    $result += \"SCOPE=$($script:scope)\"" fn)
  (write-line "    foreach ($k in 'HATCH', 'FILL', 'SOLID') { $result += \"$k=$($script:hs[$k])\" }" fn)
  (write-line "} else {" fn)
  (write-line "    $result += 'CANCEL'" fn)
  (write-line "}" fn)
  (write-line "" fn)
  (write-line "Set-Content -LiteralPath $OutputPath -Value $result -Encoding Default" fn)
  (close fn)
  (princ)
)

;; --- ブロック参照が使っている定義名(ダイナミックブロックは元の定義名も) --
(defun qsbc-ref-names (obj / nm en res)
  (setq nm (vla-get-Name obj))
  (setq res (list nm))
  (setq en (vl-catch-all-apply 'vla-get-EffectiveName (list obj)))
  (if (and (not (vl-catch-all-error-p en)) (/= (strcase en) (strcase nm)))
    (setq res (append res (list en)))
  )
  res
)

;; --- 選択ブロックから (調べる定義名一覧 表示用ブロック名一覧) を得る ------
(defun qsbc-get-selected-block-names (ss / i obj defs disp en)
  (setq i 0)
  (repeat (sslength ss)
    (setq obj (vlax-ename->vla-object (ssname ss i)))
    (foreach n (qsbc-ref-names obj)
      (if (not (member n defs)) (setq defs (cons n defs)))
    )
    (setq en (vla-get-EffectiveName obj))
    (if (not (member en disp)) (setq disp (cons en disp)))
    (setq i (1+ i))
  )
  (list (reverse defs) (reverse disp))
)

;; --- 外部参照の定義か ---------------------------------------------------
(defun qsbc-xref-p (blk / res)
  (setq res (vl-catch-all-apply 'vla-get-IsXRef (list blk)))
  (and (not (vl-catch-all-error-p res)) (= res :vlax-true))
)

;; --- ハッチング・ソリッドの種類 : "HATCH"(模様) / "FILL"(塗りつぶし・グラデーション) / "SOLID" / nil --
(defun qsbc-hs-kind (obj / on ed)
  (setq on (vla-get-ObjectName obj))
  (cond
    ((= on "AcDbHatch")
     (setq ed (entget (vlax-vla-object->ename obj)))
     (if (or (= (cdr (assoc 70 ed)) 1) (= (cdr (assoc 450 ed)) 1)) "FILL" "HATCH")
    )
    ((member on '("AcDbSolid" "AcDbTrace")) "SOLID")
  )
)

;; --- ブロック定義内の全エンティティを集める(入れ子ブロックも展開) ------
;; *qsbc-items* に (図形 所属ブロック定義 種類) を追加。同じ定義は1回だけ調べる
(defun qsbc-collect-entities (blkName / nm blk obj)
  (setq nm (strcase blkName))
  (if (not (member nm *qsbc-visited*))
    (progn
      (setq *qsbc-visited* (cons nm *qsbc-visited*))
      (setq blk (vl-catch-all-apply 'vla-item
                  (list (vla-get-Blocks (vla-get-ActiveDocument (vlax-get-acad-object))) blkName)))
      (if (and (not (vl-catch-all-error-p blk)) (not (qsbc-xref-p blk)))
        (vlax-for obj blk
          (setq *qsbc-items* (cons (list obj blk (qsbc-hs-kind obj)) *qsbc-items*))
          (if (= (vla-get-ObjectName obj) "AcDbBlockReference")
            (foreach n (qsbc-ref-names obj) (qsbc-collect-entities n))
          )
        )
      )
    )
  )
)

;; --- 色番号・線の太さを表示用文字列に変換 -------------------------------
(defun qsbc-color-to-str (val)
  (cond
    ((= val 0) "ByBlock")
    ((= val 256) "ByLayer")
    (T (itoa val))
  )
)
(defun qsbc-lwt-to-str (val)
  (cond
    ((= val -1) "ByLayer")
    ((= val -2) "ByBlock")
    ((= val -3) "既定")
    (T (strcat (rtos (/ val 100.0) 2 2) "mm"))
  )
)

;; --- 実数を表示用の文字列に変換(小数の末尾の0は除く。例 1.0 → "1" / 0.50 → "0.5") ---
(defun qsbc-num-to-str (val / s)
  (setq s (rtos val 2 6))
  (if (vl-string-search "." s)
    (setq s (vl-string-right-trim "." (vl-string-right-trim "0" s)))
  )
  s
)

;; --- 集めた図形から 画層・線種・色・線の太さの一覧 と ハッチング等の個数 を集計 --
;; 戻り値 : (画層一覧 線種一覧 色一覧 線の太さ一覧 模様数 塗りつぶし数 ソリッド数 線種尺度一覧)
(defun qsbc-gather-data (items / layers ltypes colors lwts ltscs nH nF nS obj kind s)
  (setq layers '() ltypes '() colors '() lwts '() ltscs '() nH 0 nF 0 nS 0)
  (foreach it items
    (setq obj (car it) kind (caddr it))
    (setq s (vla-get-Layer obj))
    (if (not (member s layers)) (setq layers (cons s layers)))
    (setq s (vla-get-Linetype obj))
    (if (not (member s ltypes)) (setq ltypes (cons s ltypes)))
    (setq s (qsbc-color-to-str (vla-get-Color obj)))
    (if (not (member s colors)) (setq colors (cons s colors)))
    (setq s (qsbc-lwt-to-str (vla-get-Lineweight obj)))
    (if (not (member s lwts)) (setq lwts (cons s lwts)))
    (setq s (vl-catch-all-apply 'vla-get-LinetypeScale (list obj)))
    (if (not (vl-catch-all-error-p s))
      (progn
        (setq s (qsbc-num-to-str s))
        (if (not (member s ltscs)) (setq ltscs (cons s ltscs)))
      )
    )
    (cond
      ((= kind "HATCH") (setq nH (1+ nH)))
      ((= kind "FILL") (setq nF (1+ nF)))
      ((= kind "SOLID") (setq nS (1+ nS)))
    )
  )
  (list (reverse layers) (reverse ltypes) (reverse colors) (reverse lwts) nH nF nS
        (vl-sort ltscs '(lambda (a b) (< (atof a) (atof b)))))
)

;; --- 図面の画層名("名前<TAB>色番号")・線種名の一覧(外部参照のものは除く) --
(defun qsbc-table-names (tbl / r nm res)
  (setq r (tblnext tbl T))
  (while r
    (setq nm (cdr (assoc 2 r)))
    (if (not (or (wcmatch nm "*|*") (member (strcase nm) '("BYLAYER" "BYBLOCK"))))
      (setq res (cons (if (= tbl "LAYER")
                        (strcat nm "\t" (itoa (abs (cdr (assoc 62 r)))))
                        nm)
                      res))
    )
    (setq r (tblnext tbl))
  )
  (reverse res)
)

;; --- 入力ファイル書き出し ---------------------------------------------
(defun qsbc-write-input-file (path names info entCount / fn)
  (setq fn (open path "w"))
  (write-line "###NAMES###" fn)
  (foreach s names (write-line s fn))
  (write-line "###LAYERS###" fn)
  (foreach s (nth 0 info) (write-line s fn))
  (write-line "###ALLLAYERS###" fn)
  (foreach s (qsbc-table-names "LAYER") (write-line s fn))
  (write-line "###LTYPES###" fn)
  (foreach s (nth 1 info) (write-line s fn))
  (write-line "###ALLLTYPES###" fn)
  (foreach s (qsbc-table-names "LTYPE") (write-line s fn))
  (write-line "###COLORS###" fn)
  (foreach s (nth 2 info) (write-line s fn))
  (write-line "###LWTS###" fn)
  (foreach s (nth 3 info) (write-line s fn))
  (write-line "###LTSCALES###" fn)
  (foreach s (nth 7 info) (write-line s fn))
  (write-line "###ENTCOUNT###" fn)
  (write-line (itoa entCount) fn)
  (write-line "###BLKCOUNT###" fn)
  (write-line (itoa (length names)) fn)
  (write-line "###HATCH###" fn)
  (write-line (itoa (nth 4 info)) fn)
  (write-line "###FILL###" fn)
  (write-line (itoa (nth 5 info)) fn)
  (write-line "###SOLID###" fn)
  (write-line (itoa (nth 6 info)) fn)
  (close fn)
  (princ)
)

;; --- 出力ファイル読み込み ---------------------------------------------
(defun qsbc-read-output-file (path / fn line result)
  (setq result '())
  (if (findfile path)
    (progn
      (setq fn (open path "r"))
      (while (setq line (read-line fn))
        (setq result (cons line result))
      )
      (close fn)
    )
  )
  (reverse result)
)

;; --- "a<TAB>b<TAB>c" を ("a" "b" "c") に分ける ---
(defun qsbc-split-tab (s / res pos)
  (while (setq pos (vl-string-search "\t" s))
    (setq res (cons (substr s 1 pos) res)
          s (substr s (+ pos 2)))
  )
  (reverse (cons s res))
)

;; --- 線種を設定。ByLayer/ByBlock が通らない場合は entmod で設定。失敗時は線種名つきでエラーにする ---
(defun qsbc-put-ltype (obj nm / r ed)
  (setq r (vl-catch-all-apply 'vla-put-Linetype (list obj nm)))
  (if (vl-catch-all-error-p r)
    (if (member (strcase nm) '("BYLAYER" "BYBLOCK"))
      (progn
        (setq ed (entget (vlax-vla-object->ename obj)))
        (if (assoc 6 ed)
          (setq ed (subst (cons 6 (strcase nm)) (assoc 6 ed) ed))
          (setq ed (append ed (list (cons 6 (strcase nm)))))
        )
        (if (not (entmod ed)) (error (strcat "線種「" nm "」を設定できません")))
      )
      (error (strcat "線種「" nm "」: " (vl-catch-all-error-message r)))
    )
  )
)

;; --- 線種の置き換えルール ltMap : (("変更後" "変更前1" "変更前2"...) ...) 名前は大文字
;;     oldLt が当てはまるルールの変更後を返す。なければ dflt ---
(defun qsbc-map-ltype (oldLt ltMap dflt / res)
  (foreach r ltMap
    (if (and (not res) (member oldLt (cdr r))) (setq res (car r)))
  )
  (if res res dflt)
)

;; --- 集めた図形に画層・線種・線種尺度・色・線の太さを反映。戻り値は (成功数 失敗数) --
;; scope : "ALL" すべて / "HS" ハッチング・ソリッドのみ / "OTHER" それ以外のみ
;; ltscVal : 線種尺度(実数。nil なら変更しない)
;; ltscMode : "ALL" 適用先のすべての図形 / "TYPE" ltscTypes(大文字の線種名のリスト)の図形だけ
;;            線種の判定は、線種を変更する前の線種で行う
(defun qsbc-apply-changes (items scope newLayer newLtype colorSpec lineweightSpec ltscVal ltscMode ltscTypes ltMap
                           / okCnt errCnt obj kind res oldLt chg tgt)
  (setq okCnt 0 errCnt 0 *qsbc-lasterr* nil)
  (foreach it items
    (setq obj (car it) kind (caddr it))
    (if (cond ((= scope "HS") kind) ((= scope "OTHER") (not kind)) (T T))
      (progn
        (setq res
          (vl-catch-all-apply
            '(lambda ()
               (setq chg nil)
               (setq oldLt (strcase (vla-get-Linetype obj)))
               (if newLayer (progn (vla-put-Layer obj newLayer) (setq chg T)))
               (setq tgt (qsbc-map-ltype oldLt ltMap newLtype))
               (if tgt (progn (qsbc-put-ltype obj tgt) (setq chg T)))
               (if (and ltscVal (or (/= ltscMode "TYPE") (member oldLt ltscTypes)))
                 (progn (vla-put-LinetypeScale obj ltscVal) (setq chg T))
               )
               (cond
                 ((= colorSpec "BYLAYER") (vla-put-Color obj 256) (setq chg T))
                 ((= colorSpec "BYBLOCK") (vla-put-Color obj 0) (setq chg T))
                 (colorSpec (vla-put-Color obj (atoi colorSpec)) (setq chg T))
               )
               (cond
                 ((= lineweightSpec "BYLAYER") (vla-put-Lineweight obj -1) (setq chg T))
                 ((= lineweightSpec "BYBLOCK") (vla-put-Lineweight obj -2) (setq chg T))
                 ((= lineweightSpec "DEFAULT") (vla-put-Lineweight obj -3) (setq chg T))
                 (lineweightSpec (vla-put-Lineweight obj (atoi lineweightSpec)) (setq chg T))
               )
               chg
             )
            nil
          )
        )
        (if (vl-catch-all-error-p res)
          (progn (setq errCnt (1+ errCnt)) (if (not *qsbc-lasterr*) (setq *qsbc-lasterr* (vl-catch-all-error-message res))))
          (if res (setq okCnt (1+ okCnt)))
        )
      )
    )
  )
  (list okCnt errCnt)
)

;; ============================================================
;;  ハッチング・ソリッドの分解(輪郭線化)
;;  作った図形は *qsbc-made* に入れ、途中で失敗したら消して元に戻す
;; ============================================================

(defun qsbc-2d (p) (list (car p) (cadr p)))
(defun qsbc-deg->rad (d) (* pi (/ d 180.0)))
(defun qsbc-ocs->wcs (p elev nrm) (trans (list (car p) (cadr p) elev) nrm 0))
(defun qsbc-normal (ed) (cond ((cdr (assoc 210 ed))) ('(0.0 0.0 1.0))))

;; --- 元の図形の画層・色・線種・線の太さを引き継ぐ ------------------------
(defun qsbc-copy-props (src dst)
  (foreach p '(Layer Color Linetype Lineweight LinetypeScale)
    (vl-catch-all-apply '(lambda () (vlax-put-property dst p (vlax-get-property src p))) nil)
  )
)

;; --- ブロック定義に閉じたポリラインを追加(pts は OCS の2D点、bulges は各頂点のふくらみ) --
(defun qsbc-add-poly (src blk pts bulges elev nrm / arr pl i)
  (if (>= (length pts) 2)
    (progn
      (setq arr (vlax-make-safearray vlax-vbDouble (cons 0 (1- (* 2 (length pts))))))
      (vlax-safearray-fill arr (apply 'append (mapcar 'qsbc-2d pts)))
      (setq pl (vla-AddLightWeightPolyline blk (vlax-make-variant arr)))
      (setq *qsbc-made* (cons pl *qsbc-made*))
      (setq i 0)
      (foreach b bulges
        (if (not (equal b 0.0 1e-12)) (vla-SetBulge pl i b))
        (setq i (1+ i))
      )
      (vla-put-Closed pl :vlax-true)
      (if (and elev (not (equal elev 0.0 1e-12))) (vla-put-Elevation pl elev))
      (if (not (equal nrm '(0.0 0.0 1.0) 1e-9)) (vla-put-Normal pl (vlax-3d-point nrm)))
      (qsbc-copy-props src pl)
    )
  )
)

;; --- entmakeで一時的に作った図形をブロック定義へコピーし、一時図形は消す --
(defun qsbc-entmake-into (blk src dxf / en arr res)
  (if (not (entmake dxf))
    (car 'qsbc-entmake-error) ; わざとエラーにして呼び出し元で捕まえる
  )
  (setq en (entlast))
  (setq arr (vlax-make-safearray vlax-vbObject '(0 . 0)))
  (vlax-safearray-put-element arr 0 (vlax-ename->vla-object en))
  (setq res (vl-catch-all-apply 'vla-CopyObjects
              (list (vla-get-ActiveDocument (vlax-get-acad-object)) arr blk)))
  (entdel en)
  (if (vl-catch-all-error-p res)
    (car 'qsbc-copy-error)
  )
  (foreach o (vlax-safearray->list (vlax-variant-value res))
    (setq *qsbc-made* (cons o *qsbc-made*))
    (qsbc-copy-props src o)
  )
)

;; --- 2Dソリッド → 閉じたポリライン(頂点順は 10→11→13→12) --------------
(defun qsbc-solid-outline (obj blk ed / p1 p2 p3 p4 pts)
  (setq p1 (cdr (assoc 10 ed)) p2 (cdr (assoc 11 ed))
        p3 (cdr (assoc 12 ed)) p4 (cdr (assoc 13 ed)))
  (setq pts (list p1 p2 p4))
  (if (not (equal p3 p4 1e-9)) (setq pts (append pts (list p3))))
  (qsbc-add-poly obj blk pts (mapcar '(lambda (p) 0.0) pts) (caddr p1) (qsbc-normal ed))
)

;; --- ハッチングのDXFデータを順に読む ------------------------------------
(defun qsbc-peek () (car (car *qsbc-dl*)))
(defun qsbc-take (code / p)
  (while (and *qsbc-dl* (/= (car (car *qsbc-dl*)) code))
    (setq *qsbc-dl* (cdr *qsbc-dl*))
  )
  (if (null *qsbc-dl*)
    (car 'qsbc-parse-error) ; 見つからない → わざとエラーにして呼び出し元で捕まえる
  )
  (setq p (car *qsbc-dl*) *qsbc-dl* (cdr *qsbc-dl*))
  (cdr p)
)

;; --- 境界エッジを1つ読む : (LINE 始点 終点) / (ARC 中心 半径 開始角 終了角 反時計回り) /
;;     (ELLIPSE 中心 長軸 比率 開始角 終了角 反時計回り) / (SPLINE 次数 有理 周期 ノット 制御点 重み) --
(defun qsbc-read-edge ( / typ deg rat per nk nc nf knots ctrl wts)
  (setq typ (qsbc-take 72))
  (cond
    ((= typ 1) (list 'LINE (qsbc-take 10) (qsbc-take 11)))
    ((= typ 2) (list 'ARC (qsbc-take 10) (qsbc-take 40) (qsbc-take 50) (qsbc-take 51) (qsbc-take 73)))
    ((= typ 3) (list 'ELLIPSE (qsbc-take 10) (qsbc-take 11) (qsbc-take 40) (qsbc-take 50) (qsbc-take 51) (qsbc-take 73)))
    ((= typ 4)
     (setq deg (qsbc-take 94) rat (qsbc-take 73) per (qsbc-take 74) nk (qsbc-take 95) nc (qsbc-take 96))
     (repeat nk (setq knots (cons (qsbc-take 40) knots)))
     (repeat nc
       (setq ctrl (cons (qsbc-take 10) ctrl))
       (if (= (qsbc-peek) 42) (setq wts (cons (qsbc-take 42) wts)))
     )
     ;; フィット点のデータがあれば読み飛ばす(境界の参照図形数の97と区別する)
     (if (and (= (qsbc-peek) 97) (member (car (cadr *qsbc-dl*)) '(11 12 13 72 97)))
       (progn
         (setq nf (qsbc-take 97))
         (repeat nf (qsbc-take 11))
         (if (= (qsbc-peek) 12) (qsbc-take 12))
         (if (= (qsbc-peek) 13) (qsbc-take 13))
       )
     )
     (list 'SPLINE deg rat per (reverse knots) (reverse ctrl) (reverse wts))
    )
    (T (car 'qsbc-parse-error))
  )
)

;; --- 線分と円弧だけのループ → 閉じたポリライン1本 -----------------------
;; 時計回り(73=0)の円弧は、角度が反転した座標系で記録されている
(defun qsbc-edges->poly (obj blk edges elev nrm / pts bulges c r sa ea sw a0 dir)
  (foreach e edges
    (if (eq (car e) 'LINE)
      (setq pts (cons (qsbc-2d (cadr e)) pts) bulges (cons 0.0 bulges))
      (progn
        (setq c (qsbc-2d (cadr e)) r (caddr e)
              sa (qsbc-deg->rad (nth 3 e)) ea (qsbc-deg->rad (nth 4 e)))
        (setq sw (- ea sa))
        (while (<= sw 1e-9) (setq sw (+ sw (* 2 pi))))
        (while (> sw (+ (* 2 pi) 1e-9)) (setq sw (- sw (* 2 pi))))
        (if (= (nth 5 e) 0) (setq a0 (- sa) dir -1.0) (setq a0 sa dir 1.0))
        (if (>= sw (- (* 2 pi) 1e-6))
          ;; 全円は半円2つに分ける
          (setq pts (cons (polar c (+ a0 (* dir pi)) r) (cons (polar c a0 r) pts))
                bulges (cons dir (cons dir bulges)))
          (setq pts (cons (polar c a0 r) pts)
                bulges (cons (* dir (/ (sin (/ sw 4.0)) (cos (/ sw 4.0)))) bulges))
        )
      )
    )
  )
  (qsbc-add-poly obj blk (reverse pts) (reverse bulges) elev nrm)
)

;; --- 楕円・スプラインを含むループ → エッジごとに図形を作る --------------
(defun qsbc-make-edge (obj blk e elev nrm ed / lay sa ea dxf)
  (setq lay (cons 8 (cdr (assoc 8 ed))))
  (setq dxf
    (cond
      ((eq (car e) 'LINE)
       (list '(0 . "LINE") lay
             (cons 10 (qsbc-ocs->wcs (cadr e) elev nrm))
             (cons 11 (qsbc-ocs->wcs (caddr e) elev nrm))))
      ((eq (car e) 'ARC)
       (if (= (nth 5 e) 0)
         (setq sa (- (nth 4 e)) ea (- (nth 3 e)))
         (setq sa (nth 3 e) ea (nth 4 e)))
       (list '(0 . "ARC") lay
             (cons 10 (list (car (cadr e)) (cadr (cadr e)) elev)) (cons 40 (caddr e))
             (cons 50 (qsbc-deg->rad sa)) (cons 51 (qsbc-deg->rad ea)) (cons 210 nrm)))
      ((eq (car e) 'ELLIPSE)
       (if (= (nth 6 e) 0)
         (setq sa (- 360.0 (nth 5 e)) ea (- 360.0 (nth 4 e)))
         (setq sa (nth 4 e) ea (nth 5 e)))
       (list '(0 . "ELLIPSE") '(100 . "AcDbEntity") lay '(100 . "AcDbEllipse")
             (cons 10 (qsbc-ocs->wcs (cadr e) elev nrm))
             (cons 11 (trans (list (car (caddr e)) (cadr (caddr e)) 0.0) nrm 0 T))
             (cons 210 nrm) (cons 40 (nth 3 e))
             (cons 41 (qsbc-deg->rad sa)) (cons 42 (qsbc-deg->rad ea))))
      ((eq (car e) 'SPLINE)
       (append
         (list '(0 . "SPLINE") '(100 . "AcDbEntity") lay '(100 . "AcDbSpline") (cons 210 nrm)
               (cons 70 (+ 8 (if (= (nth 2 e) 1) 4 0) (if (= (nth 3 e) 1) 2 0)))
               (cons 71 (nth 1 e)) (cons 72 (length (nth 4 e))) (cons 73 (length (nth 5 e))) '(74 . 0))
         (mapcar '(lambda (k) (cons 40 k)) (nth 4 e))
         (mapcar '(lambda (p) (cons 10 (qsbc-ocs->wcs p elev nrm))) (nth 5 e))
         (mapcar '(lambda (w) (cons 41 w)) (nth 6 e))))
    )
  )
  (qsbc-entmake-into blk obj dxf)
)

;; --- ハッチング → 境界ループごとに輪郭線を作る ---------------------------
(defun qsbc-hatch-outline (obj blk ed / nrm elev flag n pts bulges p b edges)
  (setq nrm (qsbc-normal ed))
  (setq elev (caddr (cdr (assoc 10 ed))))
  (if (not elev) (setq elev 0.0))
  (setq *qsbc-dl* (member (assoc 91 ed) ed))
  (repeat (qsbc-take 91)
    (setq flag (qsbc-take 92))
    (if (= (logand flag 2) 2)
      ;; ポリライン境界
      (progn
        (qsbc-take 72)
        (qsbc-take 73)
        (setq n (qsbc-take 93) pts '() bulges '())
        (repeat n
          (setq p (qsbc-take 10))
          (setq b (if (= (qsbc-peek) 42) (qsbc-take 42) 0.0))
          (setq pts (cons (qsbc-2d p) pts) bulges (cons b bulges))
        )
        (setq pts (reverse pts) bulges (reverse bulges))
        ;; 終点が始点と同じなら重複を除く
        (if (and (> (length pts) 2) (equal (car pts) (last pts) 1e-9))
          (setq pts (reverse (cdr (reverse pts))) bulges (reverse (cdr (reverse bulges))))
        )
        (qsbc-add-poly obj blk pts bulges elev nrm)
      )
      ;; エッジ境界
      (progn
        (setq n (qsbc-take 93) edges '())
        (repeat n (setq edges (cons (qsbc-read-edge) edges)))
        (setq edges (reverse edges))
        (if (vl-every '(lambda (e) (member (car e) '(LINE ARC))) edges)
          (qsbc-edges->poly obj blk edges elev nrm)
          (foreach e edges (qsbc-make-edge obj blk e elev nrm ed))
        )
      )
    )
  )
)

;; --- 1つの図形を分解。作った図形の数を返す -------------------------------
(defun qsbc-outline (obj blk / ed)
  (setq ed (entget (vlax-vla-object->ename obj)))
  (if (= (vla-get-ObjectName obj) "AcDbHatch")
    (qsbc-hatch-outline obj blk ed)
    (qsbc-solid-outline obj blk ed)
  )
  (length *qsbc-made*)
)

;; --- ハッチング・ソリッドの分解/削除。戻り値は (分解数 削除数 失敗数) -----
;; acts : (("HATCH" . "EXPLODE") ("FILL" . "DELETE") ("SOLID" . "KEEP")) の形
(defun qsbc-apply-hs (items acts / nExp nDel nErr obj act res)
  (setq nExp 0 nDel 0 nErr 0)
  (foreach it items
    (setq obj (car it))
    (setq act (if (caddr it) (cdr (assoc (caddr it) acts))))
    (cond
      ((= act "DELETE")
       (if (vl-catch-all-error-p (vl-catch-all-apply 'vla-Delete (list obj)))
         (setq nErr (1+ nErr))
         (setq nDel (1+ nDel))
       )
      )
      ((= act "EXPLODE")
       (setq *qsbc-made* nil)
       (setq res (vl-catch-all-apply 'qsbc-outline (list obj (cadr it))))
       (if (and (not (vl-catch-all-error-p res)) (> res 0)
                (not (vl-catch-all-error-p (vl-catch-all-apply 'vla-Delete (list obj)))))
         (setq nExp (1+ nExp))
         (progn
           ;; 失敗したら作りかけの輪郭線を消し、元の図形は残す
           (foreach o *qsbc-made* (vl-catch-all-apply 'vla-Delete (list o)))
           (setq nErr (1+ nErr))
         )
       )
      )
    )
  )
  (setq *qsbc-made* nil *qsbc-dl* nil)
  (list nExp nDel nErr)
)

;; --- メインコマンド ----------------------------------------------------
(defun c:qsb ( / *error* doc undoOn ss names items info entCount tmpDir inFile outFile ps1File
                outLines newLayer newLtype colorSpec lineweightSpec ltscaleVal ltscaleMode ltscaleTypes ltMap scope acts eqPos key val
                propChange hsChange applyResult hsResult)
  (setq doc (vla-get-ActiveDocument (vlax-get-acad-object)))
  (defun *error* (msg)
    (if (not (wcmatch (strcase msg) "*CANCEL*,*QUIT*,*EXIT*,*キャンセル*"))
      (princ (strcat "\nエラー: " msg))
    )
    (if undoOn (vla-EndUndoMark doc))
    (princ)
  )
  (setq ss (ssget '((0 . "INSERT"))))
  (if (not ss)
    (princ "\n編集対象のブロックが見つかりません。")
    (progn
      (setq names (qsbc-get-selected-block-names ss))
      (setq *qsbc-visited* nil *qsbc-items* nil)
      (foreach bn (car names) (qsbc-collect-entities bn))
      (setq items (reverse *qsbc-items*))
      (setq *qsbc-visited* nil *qsbc-items* nil)
      (setq entCount (length items))

      (if (= entCount 0)
        (princ "\n対象となる図形が見つかりませんでした。")
        (progn
          (setq info (qsbc-gather-data items))
          (setq tmpDir (getenv "TEMP"))
          (setq inFile (strcat tmpDir "\\qsbc_input.txt"))
          (setq outFile (strcat tmpDir "\\qsbc_output.txt"))
          (setq ps1File (strcat tmpDir "\\qsbc_dialog.ps1"))
          (if (findfile outFile) (vl-file-delete outFile))

          (qsbc-write-input-file inFile (cadr names) info entCount)
          (qsbc-write-ps1-script ps1File)
          (qsbc-run-ps1 ps1File inFile outFile)

          (setq outLines (qsbc-read-output-file outFile))
          (setq scope "ALL" acts '() ltscaleMode "ALL")

          (if (and outLines (not (member "CANCEL" outLines)))
            (progn
              (foreach item outLines
                (setq eqPos (vl-string-search "=" item))
                (if eqPos
                  (progn
                    (setq key (substr item 1 eqPos))
                    (setq val (substr item (+ 2 eqPos)))
                    (cond
                      ((= key "LAYER") (setq newLayer val))
                      ((= key "LTYPE") (setq newLtype val))
                      ((= key "COLOR") (setq colorSpec val))
                      ((= key "LWT") (setq lineweightSpec val))
                      ((= key "LTSCALE") (setq ltscaleVal (atof val)))
                      ((= key "LTSCALEMODE") (setq ltscaleMode val))
                      ((= key "LTSCALETYPE") (setq ltscaleTypes (cons (strcase val) ltscaleTypes)))
                      ((= key "LTMAPDST") (setq ltMap (cons (list val) ltMap)))
                      ((= key "LTMAPSRC") (if ltMap (setq ltMap (cons (append (car ltMap) (list (strcase val))) (cdr ltMap)))))
                      ((= key "SCOPE") (setq scope val))
                      ((member key '("HATCH" "FILL" "SOLID")) (setq acts (cons (cons key val) acts)))
                    )
                  )
                )
              )
              (if (and ltscaleVal (<= ltscaleVal 0.0)) (setq ltscaleVal nil))
              (setq propChange (or newLayer newLtype colorSpec lineweightSpec ltscaleVal ltMap))
              (setq hsChange (vl-some '(lambda (a) (/= (cdr a) "KEEP")) acts))
              (if (or propChange hsChange)
                (progn
                  (vla-StartUndoMark doc)
                  (setq undoOn T)
                  (if propChange
                    (progn
                      (setq applyResult (qsbc-apply-changes items scope newLayer newLtype colorSpec lineweightSpec ltscaleVal ltscaleMode ltscaleTypes ltMap))
                      (princ (strcat "\n" (itoa (nth 0 applyResult)) "個の図形を更新しました。"))
                      (if ltMap (princ (strcat "\n線種の置き換えルール: " (itoa (length ltMap)) "件")))
                      (foreach r ltMap (princ (strcat "\n  " (apply 'strcat (mapcar '(lambda (s) (strcat s " ")) (cdr r))) "→ " (car r))))
                      (if *qsbc-lasterr* (princ (strcat "\n最初のエラー: " *qsbc-lasterr*)))
                      (if (> (nth 1 applyResult) 0)
                        (princ (strcat "(" (itoa (nth 1 applyResult)) "個は変更できませんでした)"))
                      )
                    )
                  )
                  (if hsChange
                    (progn
                      (setq hsResult (qsbc-apply-hs items acts))
                      (princ (strcat "\nハッチング・ソリッド: 分解 " (itoa (nth 0 hsResult))
                                     "個 / 削除 " (itoa (nth 1 hsResult)) "個"))
                      (if (> (nth 2 hsResult) 0)
                        (princ (strcat "(" (itoa (nth 2 hsResult)) "個は処理できませんでした)"))
                      )
                    )
                  )
                  (vla-EndUndoMark doc)
                  (setq undoOn nil)
                  (command "_.REGENALL")
                )
                (princ "\n変更項目が選択されなかったため、何も更新しませんでした。")
              )
            )
            (princ "\nキャンセルされました。")
          )

          (if (findfile inFile) (vl-file-delete inFile))
          (if (findfile outFile) (vl-file-delete outFile))
          (if (findfile ps1File) (vl-file-delete ps1File))
        )
      )
    )
  )
  (princ)
)

(princ "\nQSBコマンドをロードしました。ブロック内部の画層・線種・線種尺度・色・線の太さの一括変更、ハッチング・ソリッドの分解/削除は 'QSB' と入力してください。")
(princ)
