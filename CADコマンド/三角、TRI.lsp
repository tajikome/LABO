(defun c:TRI150 ( / p1 p2 p3 )
  ;; クリックした場所を一番下の頂点にする
  (setq p1 (getpoint "\n三角形の一番下の頂点をクリックしてください: "))
  
  (if p1
    (progn
      ;; 一番下の頂点(p1)から、角度60°方向へ長さ150の点(p2)を計算（右上の頂点）
      (setq p2 (polar p1 (* pi (/ 60.0 180.0)) 150.0))
      
      ;; 一番下の頂点(p1)から、角度120°方向へ長さ150の点(p3)を計算（左上の頂点）
      (setq p3 (polar p1 (* pi (/ 120.0 180.0)) 150.0))
      
      ;; 左上 -> 右上 -> 下 の順で閉じたポリラインとして描画
      (command "_.pline" p3 p2 p1 "_c")
    )
  )
  
  (princ "\n指定した点を一番下にした逆三角形を描画しました。")
  (princ)
)

(princ "\n[TRI150] コマンドがロードされました。コマンド名: TRI150")
(princ)
